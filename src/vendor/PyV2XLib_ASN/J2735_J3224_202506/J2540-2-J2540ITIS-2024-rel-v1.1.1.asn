--
-- Terms and Conditions and User License Agreement - Download and Use of ASN File
-- 
-- Copyright: Each ASN File contained herein ("File") is copyrighted and all
-- rights, title, and interest in and to each File are owned by SAE. The 
-- license contained herein applies to each File and each reference in this license
-- to "the File" or "this File" shall be construed to include each and any ASN File
-- contained herein. No rights therein are granted except as set forth in this
-- License. Any copying, transmission, modification or reproduction of the File or
-- the copyrighted material within it, in part or in whole, except as herein
-- permitted is cause for revocation of this License.
-- 
-- License: SAE International ("SAE") hereby grants to you, as an individual or as
-- a single corporate entity, a limited nonexclusive, nontransferable right to
-- download this File in an electronic format for your individual use or use by
-- a single corporate entity on one computer. One hard copy of the File can also
-- be printed for individual use or use by a single corporate entity. SAE also
-- hereby grants to you the nonexclusive, nontransferable right to use this File
-- and create derivative works using this File for your own or your own corporate
-- entity's research purposes and in the design, creation, manufacture, distribution,
-- and use of your own products. For purposes of clarification, derivative works
-- permitted under this license include derivative works or source code that do not
-- include or incorporate this File. The derivative work may use the File to create
-- source code and corresponding software programs.  Notwithstanding the foregoing,
-- you agree that you must obtain a license from SAE to create any derivative works
-- which incorporate this File or its contents.
--
-- SAE also hereby grants to you the nonexclusive, nontransferable right to copy,
-- reproduce, distribute to others the derivative works from the use of the content
-- of this File or portions thereof in or as part of your company's products.
-- You must only license, and not otherwise sell or transfer, the products, software,
-- and software documentation that incorporates content from this File, and you must
-- prohibit any licensees or others from transferring, copying, or extracting the
-- contents of this File thereof for use in their own or others' software or products.
--
-- Other than as expressly permitted herein, this File may not be copied in whole in
-- any form for distribution to other users or other computers, including without
-- limitation to other individuals or users within your own corporate entity or
-- outside your corporate entity.  This license prohibits the end user from posting
-- or distributing content via any public forum or as open access content.  If other
-- individuals in or outside your corporate entity or different cooperate entities,
-- whether related or not to your corporate entity, wish to download or copy this
-- File, they must purchase a separate individual license to do so. 
-- 
-- This File is licensed "AS IS" to you and you do hereby hold SAE harmless from your
-- use of the File or the creative or use of derivative works thereof, and you agree
-- to indemnify SAE from any and all claims or damages caused by your use,
-- reproduction, distribution to others, or application of this File or any
-- derivative works therefrom.  SAE may amend the terms of and conditions of
-- this License or cancel this License at any time in its sole discretion and
-- for any reason by reasonable notice, including without limitation by posting
-- revised terms on its website.  
--
-- General: Files that have been successfully downloaded cannot be returned for
-- refund or credit. This Agreement is the complete and exclusive statement of the
-- agreement between you and SAE and supersedes any and all prior agreements or
-- understandings, either written or oral, concerning the subject of this Agreement.
-- Any modifications must be in writing and signed by the parties.
-- 
-- Notice to Resellers: Authorized resellers of SAE Files may download this File on
-- behalf of their customers and forward it directly, unopened, to their customers
-- provided their customers agree to abide by the terms of this License. Resellers
-- may not otherwise copy, transmit, modify or reproduce this File.
-- 
-- This license will remain in effect for the life of the standards associated with
-- the File unless otherwise amended or cancelled by SAE in its sole discretion.
-- In the event that the associated standard is cancelled or recalled due to interest
-- of public safety, the aforementioned License will be rescinded as well. This 
-- License shall terminate upon violation of any of its terms.
--
-- (C)2024 SAE International.  All rights reserved.  SAE International retains the
-- right to entertain or negotiate requests for customized distribution agreements
-- for multi-user or corporate use and / or distribution. Requests should be submitted
-- to customerservice@sae.org.
--

--
-- Use of this module defined in SAE J2540/2
-- Latest document release for this module is Dec 2020
-- Filename: J2540-2-J2540ITIS-2024-rel-v1.1.1.asn 
--

J2540ITIS
{joint-iso-itu-t(2) country (16) us (840) organization (1) sae (114566) 
v2x-communications (1) technical-committees (1) v2x-core (5) technical-reports (1) 
itis-phrase-lists (2540) part-2 (2) asn1 (1) 
version-1 (1) version-minor-1 (1)}

DEFINITIONS AUTOMATIC TAGS ::= 
BEGIN 

AccidentsAndIncidents ::= INTEGER  { 
   -- Accidents
   accident                               (513),  -- Use when no further data is
                                                  -- available regarding involved vehicle
                                                  -- type
   serious-accident                       (514),  
   injury-accident                        (515),  
   minor-accident                         (516),  
   multi-vehicle-accident                 (517),  -- To be used when events are NOT
                                                  -- distributed along a road segment
                                                  -- (i.e., one location)
   numerous-accidents                     (518),  -- To be used when events are
                                                  -- distributed along a road segment
   accident-involving-a-bicycle           (519),  
   accident-involving-a-bus               (520),  
   accident-involving-a-motorcycle        (521),  
   accident-involving-a-pedestrian        (522),  
   accident-involving-a-train             (523),  
   accident-involving-a-truck             (524),  
   accident-involving-a-semi-trailer      (562),  
   accident-involving-hazardous-materials (525),  
   earlier-accident                       (526),  -- Hint: Typically used as a cause, as
                                                  -- with "Due to"
   medical-emergency                      (527),  
   secondary-accident                     (528),  
   rescue-and-recovery-work-REMOVED       (529),  -- Removed, use Rescue and recovery
                                                  -- work in progress in the Incident
                                                  -- Response Status group when needed
   accident-investigation-work            (530),  
   incident                               (531),  -- Hint: For non-accident incidents
                                                  -- (disabled, police pull over, etc.)
                                                  -- where no further information is
                                                  -- available
   -- Disabled, etc.
   stalled-vehicle                        (532),  
   abandoned-vehicle                      (533),  
   disabled-vehicle                       (534),  
   disabled-truck                         (535),  
   disabled-semi-trailer                  (536),  -- Alternative Rendering: disabled
                                                  -- tractor-trailer
   disabled-bus                           (537),  
   disabled-train                         (538),  
   vehicle-spun-out                       (539),  
   vehicle-on-fire                        (540),  
   vehicle-in-water                       (541),  
   vehicles-slowing-to-look-at-accident   (542),  -- Alternative Rendering: On-looker
                                                  -- slowdown, Rubbernecking
   -- Jackknifed
   jackknifed-semi-trailer                (543),  -- Alternatives can use: jackknifed
                                                  -- tractor-trailer, jackknifed truck,
                                                  -- jackknifed big-rig
   jackknifed-trailer-home                (544),  
   jackknifed-trailer                     (545),  -- Hint: Used for smaller trailers
                                                  -- (i.e., not type "jackknifed semi
                                                  -- trailer" above)
   -- Spills
   spillage-occurring-from-moving-vehicle (546),  
   acid-spill                             (547),  
   chemical-spill                         (548),  
   fuel-spill                             (549),  
   hazardous-materials-spill              (550),  -- Also use the Disaster lists for
                                                  -- large HAZMAT events
   oil-spill                              (551),  
   spilled-load                           (552),  
   toxic-spill                            (553),  
   -- Overturned. Stuck
   overturned-vehicle                     (554),  -- Use when no further data is
                                                  -- available regarding involved vehicle
                                                  -- types
   overturned-truck                       (555),  
   overturned-semi-trailer                (556),  
   overturned-bus                         (557),  
   derailed-train                         (558),  
   stuck-vehicle                          (559),  -- It is preferred to provide data
                                                  -- which denotes WHY the vehicle is
                                                  -- stuck (i.e., mud/snow, under bridge,
                                                  -- too wide, etc.)
   truck-stuck-under-bridge               (560),  -- Alternative Rendering: high load
                                                  -- hit involving truck
   bus-stuck-under-bridge                 (561),  -- Alternative Rendering: high load
                                                  -- hit involving bus
   -- Cancel Types
   accident-cleared                       (638),  
   incident-cleared                       (639)
   } (0..65535)

AlternateRoute ::= INTEGER  { 
   detour-where-possible                           (8449),  
   no-detour-available                             (8450),  
   follow-signs                                    (8451),  
   follow-detour-signs                             (8452),  
   follow-special-detour-markers                   (8453),  
   do-not-follow-detour-signs                      (8454),  
   detour-in-operation                             (8455),  
   follow-local-detour                             (8456),  
   compulsory-detour-in-operation                  (8457),  
   no-suitable-detour-available                    (8458),  
   detour-is-no-longer-recommended                 (8459),  
   local-drivers-are-recommended-to-avoid-the-area (8460),  
   trucks-are-recommended-to-avoid-the-area        (8461),  
   consider-alternate-route                        (8462),  
   consider-alternate-parking                      (8463),  
   consider-alternate-destination                  (8464),  
   consider-alternate-area                         (8465),  
   -- Specific Route Types
   snow-route                                      (8466),  
   emergency-snow-route                            (8467),  
   evacuation-route                                (8468),  -- May be preceded by a
                                                            -- specific type, Used also
                                                            -- for general emergency
                                                            -- routes.
   truck-route                                     (8469),  
   hazardous-materials-route                       (8470),  -- May be used with 'any
                                                            -- time' for allowed, or 'no'
                                                            -- for prohibited, or
                                                            -- 'detour'
   detour                                          (8471)
   } (0..65535)


AssetStatus ::= INTEGER  { 
   unknown-status       (10240),  -- Used when status is not known
   ready-for-use        (10241),  
   working-normally     (10242),  
   working-autonomously (10243),  
   working-incorrectly  (10244),  
   not-working          (10245),  
   normal-maintenance   (10246),  
   in-route-to-use      (10247),  
   returning-from-use   (10248),  
   out-of-service       (10249),  
   off-duty             (10250),  
   on-patrol            (10251),  
   on-call              (10252),  
   on-break             (10253),  
   mandatory-time-off   (10254),  
   low-on-fuel          (10255),  
   low-on-water         (10256),  
   low-charge           (10257),  
   missing              (10258)   -- Use "sign down" in device status if an object is
                                  -- damaged (or use "damaged") and could be returned to
                                  -- service, use "missing" only if an object is in fact
                                  -- missing
   } (0..65535)


Closures ::= INTEGER  { 
   closed-to-traffic      (769),  -- Used for road-closed and variations
   closed                 (770),  -- Hint: use this only for NON road-lane items (such as
                                  -- a rest stop)
   closed-ahead           (771),  
   closed-intermittently  (772),  
   closed-for-repairs     (773),  
   closed-for-the-season  (774),  
   blocked                (775),  
   blocked-ahead          (776),  
   reduced-to-one-lane    (777),  
   reduced-to-two-lanes   (778),  
   reduced-to-three-lanes (779),  
   collapse               (780),  -- Used with bridges and tunnels
   out                    (781),  -- Used with bridges and roads
   -- Cancel Types
   open-to-traffic        (891),  
   open                   (892),  -- Hint: use this only for NON road-lane items (such as
                                  -- a rest stop)
   reopened-to-traffic    (893),  
   clearing               (894),  
   cleared-from-road      (895)
   } (0..65535)
   -- Combine with lane-roadway (or generic locations) as needed to form things like
   -- "toll lane closed ahead"


DelayStatusCancellation ::= INTEGER  { 
   -- Delays
   delays                             (1537),  
   short-delays                       (1538),  
   long-delays                        (1539),  
   very-long-delays                   (1540),  
   delays-of-uncertain-duration       (1541),  
   delayed-until-further-notice       (1542),  
   busy                               (1543),  -- Hint: Combine with generic locations
                                               -- (station busy, etc.)
   very-busy                          (1544),  
   crowded                            (1545),  
   overcrowded                        (1546),  
   -- Cancellations
   cancellations                      (1547),  
   route-canceled-and-no-replacement (1548),  
   service-canceled                  (1549),  
   service-suspended                  (1550),  
   service-withdrawn                  (1551),  
   service-fully-booked               (1552),  
   all-services-fully-booked          (1553),  
   -- Service Levels
   next-departure                     (1554),  -- Typically followed by a time value
   next-arrival                       (1555),  -- Typically followed by a # value of time
   very-frequent-service              (1556),  
   frequent-service                   (1557),  
   fairly-frequent-service            (1558),  
   regular-service                    (1559),  
   irregular-service                  (1560),  
   not-operating                      (1561),  
   -- Other
   system-busy                        (1562),  -- In this context "system" means the
                                               -- entire network of services over a wide
                                               -- area such as an airline system
   system-very-busy                   (1563),  
   system-crowded                     (1564),  
   system-overcrowded                 (1565),  
   deleted-travel-time                (1566),  -- A duplicate entry, now removed in favor
                                               -- of item 269
   headway                            (1567),  -- Typically followed by a # value of time
   extra-services-in-operation        (1568),  
   -- Cancel Types
   delays-clearing                    (1660),  
   delays-cleared                     (1661),  
   normal-services-resumed            (1662),  
   operating                          (1663)   -- Use operating for "services" such as
                                               -- bus service
   } (0..65535)


DeviceStatus ::= INTEGER  { 
   lane-control-signs-not-working                   (2305),  
   lane-control-signs-working-incorrectly           (2306),  
   lane-control-signs-operating                     (2307),  
   variable-message-signs-not-working               (2308),  
   variable-message-signs-working-incorrectly       (2309),  
   variable-message-signs-operating                 (2310),  
   emergency-telephones-not-working                 (2311),  
   emergency-telephone-number-not-working           (2312),  
   traffic-lights-not-working                       (2313),  
   traffic-lights-working-incorrectly               (2314),  
   ramp-control-signals-not-working                 (2315),  
   ramp-control-signals-working-incorrectly         (2316),  
   temporary-traffic-lights-not-working             (2317),  
   temporary-traffic-lights-working-incorrectly     (2318),  
   traffic-signal-control-computer-not-working      (2319),  
   traffic-signal-timings-changed                   (2320),  
   overheight-warning-system-triggered              (2321),  
   equipment-failure                                (2322),  
   railroad-crossing-equipment-failure              (2323),  
   tunnel-ventilation-not-working                   (2324),  
   power-failure                                    (2325),  -- Hint: Use for localized
                                                             -- cases of power loss
   widespread-power-outages                         (2326),  -- Alternative  rendering:
                                                             -- widespread power cuts
   technical-problems                               (2327),  
   sign-down                                        (2328),  
   lines-in-road-faded                              (2329),  
   damaged-light-standard                           (2330),  -- Used for all forms of
                                                             -- pole/support damage
   traffic-signal-stuck-on-flash                    (2331),  
   guide-rail                                       (2332),  -- Used for barriers as well
   fencing                                          (2333),  
   light-standard-hanging-by-wires                  (2334),  
   call-box                                         (2335),  
   signal-cabinet                                   (2336),  -- Use for all types of
                                                             -- equipment cabinets
   detector                                         (2337),  -- All forms of vehicle
                                                             -- detectors
   improper-use-of-State-vehicle-or-equipment       (2338),  
   bulb-out                                         (2339),  
   not-yet-operational                              (2340),  -- When installed but not
                                                             -- yet brought on-line for
                                                             -- use by the system
   not-yet-installed                                (2341),  -- When planned
   -- Cancel Types
   electronic-signs-repaired                        (2428),  
   emergency-call-facilities-restored               (2429),  
   traffic-signals-repaired                         (2430),  
   railroad-crossing-equipment-now-working-normally (2431)
   } (0..65535)


Disasters ::= INTEGER  { 
   -- Water Related
   flash-flood                       (3073),  
   major-flood                       (3074),  
   reservoir-failure                 (3075),  
   levee-failure                     (3076),  
   tsunami                           (3077),  
   tidal-wave                        (3078),  
   -- Fire Related
   volcanic-eruption                 (3079),  
   ash-fall                          (3080),  
   lava-flow                         (3081),  
   serious-fire                      (3082),  
   forest-fire                       (3083),  
   wildfire                          (3084),  
   building-fire                     (3085),  
   brush-fire                        (3086),  
   grass-fire                        (3087),  
   fire-danger-extreme               (3088),  
   fire-danger-very-high             (3089),  
   fire-danger-high                  (3090),  
   fire-danger-medium                (3091),  
   fire-danger-low                   (3092),  
   --  Other
   earthquake-damage                 (3093),  
   air-crash                         (3094),  
   rail-crash                        (3095),  
   toxic-release                     (3096),  
   toxic-leak                        (3097),  
   radioactive-release               (3098),  
   radiation-hazard                  (3099),  
   reactor-leakage                   (3100),  
   explosion                         (3101),  
   major-hazardous-materials-fire    (3102),  -- Alternative Rendering: Major HAZMAT
                                              -- fire
   major-hazardous-materials-release (3103),  -- Alternative Rendering: Major HAZMAT
                                              -- release
   -- Cancel Types
   disaster-cleared                  (3199)
   } (0..65535)


Disturbances ::= INTEGER  { 
   assault                            (3329),  -- This index is not to be used as a
                                               -- default value for this category
   crime                              (3330),  
   robbery                            (3331),  
   fare-dispute                       (3332),  
   shooting                           (3333),  
   gunfire-on-roadway                 (3334),  
   suicide                            (3335),  
   fight                              (3336),  -- Involves a few  persons and is
                                               -- localized (alt: brawl)
   gang-fight                         (3337),  -- Multi-party event occurring which may
                                               -- involve weapons
   person-harassment                  (3338),  -- "person" may be rendered as "passenger"
                                               -- if used in a controlled environment
                                               -- such as transit
   person-injured                     (3339),  
   sick-customer                      (3363),  
   unruly-passenger                   (3340),  
   person-intoxicated                 (3341),  
   crowd-control-problem              (3342),  
   demonstration                      (3343),  
   march                              (3344),  
   public-disturbance                 (3345),  
   riot                               (3346),  
   civil-unrest                       (3347),  
   civil-emergency                    (3348),  
   strike                             (3349),  
   public-transit-strike              (3350),  -- Hint: Strike affecting services
   stampede                           (3351),  
   teargas-used                       (3352),  
   security-alert                     (3353),  -- Heightened security procedures in
                                               -- effect
   security-incident                  (3354),  
   checkpoint                         (3355),  
   bomb-alert                         (3356),  
   terrorist-incident                 (3357),  
   high-velocity-shell-fire           (3358),  -- Hint: Used as a part of avalanche
                                               -- control
   explosives-in-use                  (3359),  
   air-raid                           (3360),  
   weapons-of-mass-destruction-threat (3361),  
   military-operations                (3362),  -- (war)
   -- Cancel Types
   security-problem-cleared           (3454),  
   traffic-disturbance-cleared        (3455)
   } (0..65535)
   -- Disturbances occurring on or affecting the actual roadway or surrounding areas


GenericLocations ::= INTEGER  { 
   -- Road Related
   on-bridges                  (7937),  -- Not to be used as the default for this
                                        -- category
   in-tunnels                  (7938),  
   entering-or-leaving-tunnels (7939),  
   on-ramps                    (7940),  
   in-road-construction-area   (7941),  
   around-a-curve              (7942),  
   on-curve                    (8026),  
   on-tracks                   (8009),  
   in-street                   (8025),  -- As in in-street pad crossing
   shoulder                    (8027),  
   on-minor-roads              (7943),  
   in-the-opposing-lanes       (7944),  
   adjacent-to-roadway         (7945),  
   across-tracks               (8024),  
   on-bend                     (7946),  
   intersection                (8032),  
   entire-intersection         (7947),  
   in-the-median               (7948),  
   moved-to-side-of-road       (7949),  
   moved-to-shoulder           (7950),  
   on-the-roadway              (7951),  -- Use generic locations and groups affected to
                                        -- make other such phrases
   dip                         (8010),  
   traffic-circle              (8011),  -- Used for W2-6 graphic as well. Alt term:
                                        -- roundabout
   crossover                   (8028),  
   cross-road                  (8029),  -- Also used for W2-1 Note that in some uses
                                        -- this is one word
   side-road                   (8030),  -- Do not used for W2-2R and W2-2L
   to                          (8014),  
   by                          (8015),  
   through                     (8016),  
   area-of                     (8017),  -- Also area
   under                       (8018),  
   over                        (8019),  
   from                        (8020),  
   approaching                 (8021),  
   entering-at                 (8022),  -- Alt form: Entrance
   exiting-at                  (8023),  
   -- Terrain & Geography
   in-shaded-areas             (7952),  
   in-low-lying-areas          (7953),  
   in-the-downtown-area        (7954),  
   in-the-inner-city-area      (7955),  
   in-parts                    (7956),  
   in-some-places              (7957),  
   in-the-ditch                (7958),  
   in-the-valley               (7959),  
   on-hill-top                 (7960),  
   near-the-foothills          (7961),  
   at-high-altitudes           (7962),  
   near-the-lake               (7963),  
   near-the-shore              (7964),  
   nearby-basin                (8008),  
   over-the-crest-of-a-hill    (7965),  
   other-than-on-the-roadway   (7966),  
   near-the-beach              (7967),  
   near-beach-access-point     (7968),  
   mountain-pass               (8006),  
   lower-level                 (7969),  
   upper-level                 (7970),  
   coast                       (8034),  
   -- Transit Travel, Air Travel and Places
   airport                     (7971),  
   concourse                   (7972),  
   gate                        (7973),  
   baggage-claim               (7974),  
   customs-point               (7975),  
   reservation-center          (8007),  
   station                     (7976),  
   platform                    (7977),  -- Alternative Rendering: track
   dock                        (7978),  
   depot                       (7979),  
   ev-charging-point           (7980),  
   information-welcome-point   (7981),  -- Use for Tourist Information as well (D9-10)
   at-rest-area                (7982),  
   at-service-area             (7983),  
   at-weigh-station            (7984),  
   roadside-park               (8033),  
   picnic-areas                (7985),  
   rest-area                   (7986),  
   service-stations            (7987),  
   toilets                     (7988),  -- Note also rest rooms in structures
   bus-stop                    (8031),  
   park-and-ride-lot           (8012),  -- Not to be used as a mode of travel
   -- Direction of Travel
   on-the-right                (7989),  
   on-the-left                 (7990),  
   in-the-center               (7991),  
   in-the-opposite-direction   (7992),  
   cross-traffic               (7993),  
   northbound-traffic          (7994),  
   eastbound-traffic           (7995),  
   southbound-traffic          (7996),  
   westbound-traffic           (7997),  
   -- Compass Points
   north                       (7998),  
   south                       (7999),  
   east                        (8000),  
   west                        (8001),  
   northeast                   (8002),  
   northwest                   (8003),  
   southeast                   (8004),  
   southwest                   (8005)
   } (0..65535)


IncidentResponseEquipment ::= INTEGER  { 
   ground-fire-suppression          (9985),   
   heavy-ground-equipment           (9986),   
   aircraft                         (9988),   
   marine-equipment                 (9989),   
   support-equipment                (9990),   
   medical-rescue-unit              (9991),   
   other                            (9993),   -- Depreciated by fire standards, do not
                                              -- use
   ground-fire-suppression-other    (9994),   
   engine                           (9995),   
   truck-or-aerial                  (9996),   
   quint                            (9997),   -- A five-function type of fire apparatus.
                                              -- The units in the movie Backdraft were
                                              -- quints
   tanker-pumper-combination        (9998),   
   brush-truck                      (10000),  
   aircraft-rescue-firefighting     (10001),  
   heavy-ground-equipment-other     (10004),  
   dozer-or-plow                    (10005),  
   tractor                          (10006),  
   tanker-or-tender                 (10008),  
   aircraft-other                   (10024),  
   aircraft-fixed-wing-tanker       (10025),  
   helitanker                       (10026),  
   helicopter                       (10027),  
   marine-equipment-other           (10034),  
   fire-boat-with-pump              (10035),  
   boat-no-pump                     (10036),  
   support-apparatus-other          (10044),  
   breathing-apparatus-support      (10045),  
   light-and-air-unit               (10046),  
   medical-rescue-unit-other        (10054),  
   rescue-unit                      (10055),  
   urban-search-rescue-unit         (10056),  
   high-angle-rescue                (10057),  
   crash-fire-rescue                (10058),  
   bLS-unit                         (10059),  
   aLS-unit                         (10060),  
   mobile-command-post              (10075),  -- Deprecated, do not use
   chief-officer-car                (10076),  
   hAZMAT-unit                      (10077),  
   type-i-hand-crew                 (10078),  
   type-ii-hand-crew                (10079),  
   privately-owned-vehicle          (10083),  -- (Often found in volunteer fire teams)
   other-apparatus-resource         (10084),  -- (Remapped from fire code zero)
   ambulance                        (10085),  
   bomb-squad-van                   (10086),  
   combine-harvester                (10087),  
   construction-vehicle             (10088),  
   farm-tractor                     (10089),  
   grass-cutting-machines           (10090),  
   hAZMAT-containment-tow           (10091),  
   heavy-tow                        (10092),  
   light-tow                        (10094),  
   flatbed-tow                      (10114),  
   hedge-cutting-machines           (10093),  
   mobile-crane                     (10095),  
   refuse-collection-vehicle        (10096),  
   resurfacing-vehicle              (10097),  
   road-sweeper                     (10098),  
   survey-crews                     (10115),  
   roadside-litter-collection-crews (10099),  
   salvage-vehicle                  (10100),  
   sand-truck                       (10101),  
   snowplow                         (10102),  
   steam-roller                     (10103),  
   swat-team-van                    (10104),  
   track-laying-vehicle             (10105),  
   unknown-vehicle                  (10106),  
   white-lining-vehicle             (10107),  -- Consider using Roadwork "road marking
                                              -- operations" unless the objective is to
                                              -- refer to the specific vehicle of this
                                              -- type. Alternative Rendering: line
                                              -- painting vehicle
   dump-truck                       (10108),  
   supervisor-vehicle               (10109),  
   snow-blower                      (10110),  
   rotary-snow-blower               (10111),  
   road-grader                      (10112),  -- Alternative term: motor grader
   steam-truck                      (10113)   -- A special truck that thaws culverts and
                                              -- storm drains
   } (0..65535)


IncidentResponseStatus ::= INTEGER  { 
   unconfirmed-report                   (2817),  
   initial-response-en-route            (2818),  
   follow-up-response-en-route          (2819),  
   initial-response-on-scene            (2820),  
   follow-up-response-on-scene          (2821),  
   confirmed-report                     (2822),  
   scene-is-unsecured-at-this-time      (2823),  -- Caution: This has different meanings
                                                 -- in Public Safety use
   response-scene-secured               (2824),  -- Caution: This has different meanings
                                                 -- in Public Safety use
   rescue-and-recovery-work-in-progress (2825),  
   extraction-in-progress               (2826),  
   clearance-work-in-progress           (2827),  
   body-removal-operations              (2828),  
   fire-containment-contained           (2829),  
   fire-containment-not-contained       (2830),  
   event-cleared                        (2831),  -- Meaning that responder has left
                                                 -- scene, not that surrounding traffic
                                                 -- has cleared to a normal level
   traffic-clearing                     (2832),  
   incident-closed                      (2833)   -- A "case closed" meaning which can
                                                 -- differ considerably by local agency
                                                 -- policies
   } (0..65535)
   -- Primarily this list is used for exchanging response status with other agencies.
   -- Some of these phrases should be avoided in ITIS targeted for consumer use


SystemInformation ::= INTEGER  { 
   information-available-on-radio         (4353),  -- Not to be used as a default for
                                                   -- this category D12-1
   information-available-on-TV            (4354),  
   call-to-get-information                (4355),  
   information-available-via-Internet     (4356),  
   test-message                           (4357),  -- Not to be displayed on consumer
                                                   -- devices if possible
   no-information-available               (4358),  -- Typically combined with "on xxx
                                                   -- service" where xxx is a type of
                                                   -- service (bus, rail, etc.)
   null-description                       (4359),  -- (but with event location or other
                                                   -- information provided in the
                                                   -- message)
   police-assistance                      (4361),  
   police-monitor-CB                      (4362),  -- D12-3
   emergency-notification                 (4363),  
   in-emergency-dial-911                  (4364),  -- D12-14
   travel-Info-call-511                   (4365),  -- D`12-5
   car-pool-information                   (4366),  -- D12-2
   information-service-resumed            (4478),  
   -- Cancel Types
   information-service-is-being-suspended (4360),  
   message-canceled                       (4479)   -- Not Recommended for use
   } (0..65535)


AdviceInstructionsMandatory ::= INTEGER  { 
   keep-to-the-right                    (7425),  
   keep-to-the-left                     (7426),  
   use-right-lane                       (7427),  
   use-left-lane                        (7428),  
   stay-in-lane                         (7450),  
   merge                                (7451),  -- Typically followed by direction
                                                 -- left/right Used for W4-1R and W4-1L
   heavy-vehicles-use-right-lane        (7429),  
   heavy-vehicles-use-left-lane         (7430),  
   observe-signals                      (7431),  
   observe-signs                        (7432),  
   no-passing                           (7433),  -- Used for MUTCD signs
   no-smoking                           (7434),  
   no-open-flames                       (7435),  
   use-shoulder-as-lane                 (7436),  
   do-not-drive-on-the-shoulder         (7437),  
   allow-emergency-vehicles-to-pass     (7438),  
   clear-a-lane-for-emergency-vehicles  (7439),  
   pull-over-to-the-edge-of-the-roadway (7440),  
   wait-for-escort-vehicle              (7441),  
   in-emergency-wait-for-police-patrol  (7442),  
   reduce-your-speed                    (7443),  
   observe-speed-limits                 (7444),  
   check-point                          (7445),  
   entry-requirements                   (7446),  
   insurance-requirements               (7447),  
   firearms-requirements                (7448),  
   pet-requirements                     (7449),  
   slower-traffic-keep-right            (7452),  
   keep-off                             (7453),  -- Typically followed by object
   evacuate-area-immediately            (7454),
   -- Cancel Types
   shoulder-travel-no-longer-allowed    (7547)
   } (0..65535)


AdviceInstructionsRecommendations ::= INTEGER  { 
   drive-carefully                                             (7169),  
   drive-with-extreme-caution                                  (7170),  
   approach-with-care                                          (7171),  
   keep-your-distance                                          (7172),  
   increase-normal-following-distance                          (7173),  
   test-your-brakes                                            (7174),  
   cross-intersection-with-care                                (7175),  
   pass-with-care                                              (7176),  -- Use as MUTCD
                                                                        -- sign
   pass                                                        (7200),  -- Used for
                                                                        -- passing
                                                                        -- action, as in
                                                                        -- do not pass
   use-low-beam-headlights                                     (7177),  
   use-fog-lights                                              (7178),  
   use-hazard-warning-lights                                   (7179),  -- Alternative
                                                                        -- Rendering:
                                                                        -- use blinkers
   do-not-leave-your-vehicle                                   (7180),  
   leave-your-vehicle-and-proceed-to-next-safe-place           (7181),  
   turn-off-engine                                             (7182),  -- Alternative
                                                                        -- Rendering:
                                                                        -- switch off
                                                                        -- engine
   close-all-windows-turn-off-heater-air-conditioner-and-vents (7183),  
   turn-off-air-conditioner-to-prevent-engine-overheating      (7184),  
   turn-off-mobile-phones-and-two-way-radios                   (7185),  -- Alternative
                                                                        -- Rendering:
                                                                        -- switch off
                                                                        -- mobile phones
                                                                        -- and two way
                                                                        -- radios
   prepare-to-stop                                             (7186),  
   be-prepared-to-stop                                         (7201),  
   stop-at-next-rest-area                                      (7187),  
   stop-at-next-safe-place                                     (7188),  
   only-travel-if-absolutely-necessary                         (7189),  
   drive-to-another-service-area                               (7190),  
   use-through-traffic-lanes                                   (7191),  
   use-local-traffic-lanes                                     (7192),  
   use-left-hand-parallel-roadway                              (7193),  
   use-right-hand-parallel-roadway                             (7194),  
   use-heavy-vehicle-lane                                      (7195),  -- Alternative
                                                                        -- Rendering:
                                                                        -- use truck
                                                                        -- lanes
   observe-recommended-speed                                   (7196),  
   signals-sequenced-for-speed                                 (7202),  -- Typically
                                                                        -- followed by
                                                                        -- speed
   maintain-top-safe-speed                                     (7203),  
   facing-traffic                                              (7197),  
   push-button                                                 (7198),  
   to-cross-street                                             (7199),  
   evacuate-area-voluntarily                                   (7204),  
   shelter-in-place                                            (7205)
   } (0..65535)


ITIStext ::= IA5String (SIZE(1..500))

ITISgroups ::= INTEGER {
    trafficConditions                  (1),
    accidentsAndIncidents              (2),
    closures                           (3),
    roadwork                           (4),
    obstruction                        (5),
    delayStatusCancellation            (6),
    unusualDriving                     (7),
    mobileSituation                    (8),
    deviceStatus                       (9),
    restrictionClass                  (10),
    incidentResponseStatus            (11),
    disasters                         (12),
    disturbances                      (13),
    sportingEvents                    (14),
    specialEvents                     (15),
    parkingInformation                (16),
    systemInformation                 (17),
    weatherConditions                 (18),
    precipitation                     (19),
    winds                             (20),
    visibilityAndAirQuality           (21),
    temperature                       (22),
    pavementConditions                (23),
    winterDrivingRestrictions         (24),
    winterDrivingIndex                (25),
    suggestionAdvice                  (26),
    warningAdvice                     (27),
    adviceInstructionsRecommendations (28),
    adviceInstructionsMandatory       (29),
    qualifiers                        (30),
    genericLocations                  (31),
    laneRoadway                       (32),
    alternateRoute                    (33),
    units                             (34),
    transitMode                       (35),
    vehicleGroupAffected              (36),
    travelerGroupAffected             (37),
    responderGroupAffected            (38),
    incidentResponseEquipment         (39),
    assetStatus                       (40),
    roadsideAssets                    (41),
    transitOperations                 (42),
    objects                           (43),
    validManeuvers                    (44), 
    largeNumbers                      (45), 
    namedObjects                      (46), 
    recreationalObjectsAndActivities  (47), 
    regulatoryAndWarningSigns         (48), 
    smallNumbers                      (49), 
    states                            (50), 
    structures                        (51), 
    streetSuffixes                    (52), 
    mUTCDLocations                    (53)
    } (0..255)


ITIScodes ::= INTEGER  { 
   -- Traffic Conditions
   stopped-traffic                            (257),    
   stop-and-go-traffic                        (258),    
   slow-traffic                               (259),    
   heavy-traffic                              (260),    
   traffic-building                           (261),    
   long-queues                                (262),    
   traffic-congestion                         (263),    
   traffic-lighter-than-normal                (264),    
   traffic-heavier-than-normal                (265),    
   traffic-much-heavier-than-normal           (266),    
   current-speed                              (267),    -- Typically followed by a value
                                                        -- entry and a units entry
                                                        -- (MPH/KPH)
   speed-limit                                (268),    -- Typically followed by a value
                                                        -- entry and a units entry
                                                        -- (MPH/KPH)
   travel-time                                (269),    -- Typically followed by a value
                                                        -- entry and a units entry
                                                        -- (seconds)
   merging-traffic                            (272),    -- Typically followed by
                                                        -- direction left/right. Can be
                                                        -- used for W4-1R and W4-1L signs
   contraflow                                 (273),    -- also referred to as counter-flow
   -- Cancel Types
   contraflow-canceled                        (378),  
   traffic-flowing-freely                     (379),    
   traffic-easing                             (380),    -- Alternative rendering: traffic
                                                        -- clearing
   traffic-returned-to-normal                 (381),    
   no-problems-to-report                      (382),    
   traffic-congestion-cleared                 (383),    
   -- Accidents and Incidents
   -- Accidents
   accident                                   (513),    -- Use when no further data is
                                                        -- available regarding involved
                                                        -- vehicle type
   serious-accident                           (514),    
   injury-accident                            (515),    
   minor-accident                             (516),    
   multi-vehicle-accident                     (517),    -- To be used when events are NOT
                                                        -- distributed along a road
                                                        -- segment (i.e., one location)
   numerous-accidents                         (518),    -- To be used when events are
                                                        -- distributed along a road
                                                        -- segment
   accident-involving-a-bicycle               (519),    
   accident-involving-a-bus                   (520),    
   accident-involving-a-motorcycle            (521),    
   accident-involving-a-pedestrian            (522),    
   accident-involving-a-train                 (523),    
   accident-involving-a-truck                 (524),    
   accident-involving-a-semi-trailer          (562),    
   accident-involving-hazardous-materials     (525),    
   earlier-accident                           (526),    -- Hint: Typically used as a
                                                        -- cause, as with "Due to"
   medical-emergency                          (527),    
   secondary-accident                         (528),    
   rescue-and-recovery-work-REMOVED           (529),    -- Removed, use Rescue and
                                                        -- recovery work in progress in
                                                        -- the Incident Response Status
                                                        -- group when needed
   accident-investigation-work                (530),    
   incident                                   (531),    -- Hint: For non-accident
                                                        -- incidents (disabled, police
                                                        -- pull over, etc.) where no
                                                        -- further information is
                                                        -- available
   -- Disabled, etc.
   stalled-vehicle                            (532),    
   abandoned-vehicle                          (533),    
   disabled-vehicle                           (534),    
   disabled-truck                             (535),    
   disabled-semi-trailer                      (536),    -- Alternative Rendering:
                                                        -- disabled tractor-trailer
   disabled-bus                               (537),    
   disabled-train                             (538),    
   vehicle-spun-out                           (539),    
   vehicle-on-fire                            (540),    
   vehicle-in-water                           (541),    
   vehicles-slowing-to-look-at-accident       (542),    -- Alternative Rendering:
                                                        -- On-looker slowdown,
                                                        -- Rubbernecking
   -- Jackknifed
   jackknifed-semi-trailer                    (543),    -- Alternatives can use:
                                                        -- jackknifed tractor-trailer,
                                                        -- jackknifed truck, jackknifed
                                                        -- big-rig
   jackknifed-trailer-home                    (544),    
   jackknifed-trailer                         (545),    -- Hint: Used for smaller
                                                        -- trailers (i.e., not type
                                                        -- "jackknifed semi trailer"
                                                        -- above)
   -- Spills
   spillage-occurring-from-moving-vehicle     (546),    
   acid-spill                                 (547),    
   chemical-spill                             (548),    
   fuel-spill                                 (549),    
   hazardous-materials-spill                  (550),    -- Also use the Disaster lists
                                                        -- for large HAZMAT events
   oil-spill                                  (551),    
   spilled-load                               (552),    
   toxic-spill                                (553),    
   -- Overturned. Stuck
   overturned-vehicle                         (554),    -- Use when no further data is
                                                        -- available regarding involved
                                                        -- vehicle types
   overturned-truck                           (555),    
   overturned-semi-trailer                    (556),    
   overturned-bus                             (557),    
   derailed-train                             (558),    
   stuck-vehicle                              (559),    -- It is preferred to provide
                                                        -- data which denotes WHY the
                                                        -- vehicle is stuck (i.e.,
                                                        -- mud/snow, under bridge, too
                                                        -- wide, etc.)
   truck-stuck-under-bridge                   (560),    -- Alternative Rendering: high
                                                        -- load hit involving truck
   bus-stuck-under-bridge                     (561),    -- Alternative Rendering: high
                                                        -- load hit involving bus
   -- Cancel Types
   accident-cleared                           (638),    
   incident-cleared                           (639),    
   -- Closures (Road and Lane)
   closed-to-traffic                          (769),    -- Used for road-closed and
                                                        -- variations
   closed                                     (770),    -- Hint: use this only for NON
                                                        -- road-lane items (such as a
                                                        -- rest stop)
   closed-ahead                               (771),    
   closed-intermittently                      (772),    
   closed-for-repairs                         (773),    
   closed-for-the-season                      (774),    
   blocked                                    (775),    
   blocked-ahead                              (776),    
   reduced-to-one-lane                        (777),    
   reduced-to-two-lanes                       (778),    
   reduced-to-three-lanes                     (779),    
   collapse                                   (780),    -- Used with bridges and tunnels
   out                                        (781),    -- Used with bridges and roads
   -- Cancel Types
   open-to-traffic                            (891),    
   open                                       (892),    -- Hint: use this only for NON
                                                        -- road-lane items (such as a
                                                        -- rest stop)
   reopened-to-traffic                        (893),    
   clearing                                   (894),    
   cleared-from-road                          (895),    
   -- Roadwork
   -- Roads
   road-construction                          (1025),   -- Alt text: Road Work
   major-road-construction                    (1026),   
   long-term-road-construction                (1027),   
   construction-work                          (1028),   
   paving-operations                          (1029),   
   work-in-the-median                         (1030),   
   road-reconstruction                        (1031),   
   opposing-traffic                           (1032),   
   narrow-lanes                               (1033),   
   construction-traffic-merging               (1034),   
   single-line-traffic-alternating-directions (1035),   
   road-maintenance-operations                (1036),   
   road-marking-operations                    (1037),   
   road-widening                              (1061),   -- Used for roadwork, not as an
                                                        -- MUTCD sign
   cracks                                     (1052),   -- Used for disjoint roadway
                                                        -- surface
   crack-REMOVE                               (1058),   -- No Longer Used. Used for
                                                        -- disjoint roadway surface
   bumps                                      (1053),   -- Used for swelling
   drop-off                                   (1059),   
   storm-drain                                (1054),   
   -- Bridges
   bridge-maintenance-operations              (1038),   
   bridge-construction                        (1039),   
   bridge-demolition-work                     (1040),   
   seismic-retrofit                           (1060),   -- All types of earthquake
                                                        -- construction
   -- Other
   overgrown-grass                            (1055),   
   overgrown-brushshrubs                      (1056),   
   overgrown-trees                            (1057),   
   blasting                                   (1041),   -- See also: avalanche
   avalanche-control-activities               (1042),   
   water-main-work                            (1043),   
   gas-main-work                              (1044),   
   work-on-underground-cables                 (1045),   
   work-on-underground-services               (1046),   
   new-road-construction-layout               (1047),   
   new-road-layout                            (1048),   
   temporary-lane-markings                    (1049),   
   temporary-traffic-lights                   (1050),   
   emergency-maintenance                      (1051),   
   utility-work                              (1062),   
   -- Cancel Types
   road-maintenance-cleared                   (1146),   
   normal-road-layout-restored                (1147),   
   road-work-clearance-in-progress            (1148),   
   road-construction-cleared                  (1149),   
   normal-traffic-lanes-restored              (1150),   
   road-work-cleared                          (1151),   
   -- Obstructions
   -- General
   obstruction-on-roadway                     (1281),   
   object-on-roadway                          (1282),   
   objects-falling-from-moving-vehicle        (1283),   
   debris-on-roadway                          (1284),   
   storm-damage                               (1285),   
   -- People
   people-on-roadway                          (1286),   
   bicyclists-on-roadway                      (1287),   
   sightseers-obstructing-access              (1288),   
   large-numbers-of-visitors                  (1289),   
   -- Animals
   animal-on-roadway                          (1290),   
   large-animal-on-roadway                    (1291),   
   herd-of-animals-on-roadway                 (1292),   
   animal-struck                              (1293),   
   -- Specific Items
   advertising-signs                          (1315),   -- Used for illegal signage as
                                                        -- well
   fallen-trees                               (1294),   
   over-turned-trees                          (1311),   
   tree-limbs                                 (1312),   
   utility-pole-down                          (1314),   
   downed-power-lines                         (1295),   -- Alternative Rendering: fallen
                                                        -- power lines
   downed-cables                              (1296),   -- Alternative Rendering: fallen
                                                        -- cables
   subsidence                                 (1297),   -- Alternative Rendering: road
                                                        -- collapse
   road-surface-collapse                      (1298),   
   frost-jacking                              (1317),   -- A unique Alaska problem caused
                                                        -- by culverts or other features
                                                        -- jacking out of ground due to
                                                        -- freezing
   frost-heave                                (1316),   -- A large standing wave of soil
                                                        -- under pavement due to frost
                                                        -- action
   pavement-buckled                           (1299),   
   pothole                                    (1300),   
   flooding                                   (1301),   
   broken-water-main                          (1302),   
   collapsed-sewer                            (1303),   
   wash-out                                   (1319),   -- What can happen to roads
   washboard                                  (1318),   -- A term for rough road or
                                                        -- unpaved roads
   sewer-overflow                             (1304),   
   gas-leak                                   (1305),   
   snowmelt                                   (1306),   -- Hint: Typically used as a
                                                        -- cause
   mudslide                                   (1307),   
   avalanche                                  (1308),   -- Possibly a disaster as well
   rockfall                                   (1309),   
   landslide                                  (1310),   
   -- Cancel Types
   clearance-work                             (1406),   
   obstruction-cleared                        (1407),   
   -- Delays, Status, and Cancellations
   -- Delays
   delays                                     (1537),   
   short-delays                               (1538),   
   long-delays                                (1539),   
   very-long-delays                           (1540),   
   delays-of-uncertain-duration               (1541),   
   delayed-until-further-notice               (1542),   
   busy                                       (1543),   -- Hint: Combine with generic
                                                        -- locations (station busy, etc.)
   very-busy                                  (1544),   
   crowded                                    (1545),   
   overcrowded                                (1546),   
   -- Cancellations
   cancellations                              (1547),   
   route-canceled-and-no-replacement         (1548),   
   service-canceled                          (1549),   
   service-suspended                          (1550),   
   service-withdrawn                          (1551),   
   service-fully-booked                       (1552),   
   all-services-fully-booked                  (1553),   
   -- Service Levels
   next-departure                             (1554),   -- Typically followed by a time
                                                        -- value
   next-arrival                               (1555),   -- Typically followed by a #
                                                        -- value of time
   very-frequent-service                      (1556),   
   frequent-service                           (1557),   
   fairly-frequent-service                    (1558),   
   regular-service                            (1559),   
   irregular-service                          (1560),   
   not-operating                              (1561),   
   -- Other
   system-busy                                (1562),   -- In this context "system" means
                                                        -- the entire network of services
                                                        -- over a wide area such as an
                                                        -- airline system
   system-very-busy                           (1563),   
   system-crowded                             (1564),   
   system-overcrowded                         (1565),   
   deleted-travel-time                        (1566),   -- A duplicate entry, now removed
                                                        -- in favor of item 269
   headway                                    (1567),   -- Typically followed by a #
                                                        -- value of time
   extra-services-in-operation                (1568),   
   -- Cancel Types
   delays-clearing                            (1660),   
   delays-cleared                             (1661),   
   normal-services-resumed                    (1662),   
   operating                                  (1663),   -- Use operating for "services"
                                                        -- such as bus service
   -- Unusual Driving
   vehicle-traveling-wrong-way                (1793),   
   reckless-driver                            (1794),   -- Alternative Rendering:
                                                        -- erratic driver
   prohibited-vehicle-on-roadway              (1795),   
   emergency-vehicles-on-roadway              (1796),   
   high-speed-emergency-vehicles              (1797),   
   high-speed-chase                           (1798),   
   -- Cancel Types
   dangerous-vehicle-warning-cleared          (1918),   
   emergency-vehicle-warning-cleared          (1919),   
   -- Mobile Situation
   abnormal-load                              (2049),   
   wide-load                                  (2050),   
   long-load                                  (2051),   
   slow-vehicle                               (2052),   
   farm-equipment                             (2053),   
   horse-drawn-vehicles                       (2054),   
   overheight-load                            (2055),   
   overweight-load                            (2056),   
   tracked-vehicle                            (2057),   
   vehicle-carrying-hazardous-materials       (2058),   
   slow-moving-maintenance-vehicle            (2059),   -- Hint: mowing, line stripping,
                                                        -- sweepers, etc.
   convoy                                     (2060),   
   military-convoy                            (2061),   
   refugee-convoy                             (2062),   
   motorcade                                  (2063),   
   mobile-situation-repositioning             (2064),   
   winter-maintenance-vehicles                (2065),   
   snowplows                                  (2066),   
   -- Cancel Types
   slow-moving-maintenance-vehicle-warning-cleared (2172),   
   exceptional-load-warning-cleared           (2173),   
   hazardous-load-warning-cleared             (2174),   
   convoy-cleared                             (2175),   
   -- Device and Equipment Status
   lane-control-signs-not-working             (2305),   
   lane-control-signs-working-incorrectly     (2306),   
   lane-control-signs-operating               (2307),   
   variable-message-signs-not-working         (2308),   
   variable-message-signs-working-incorrectly (2309),   
   variable-message-signs-operating           (2310),   
   emergency-telephones-not-working           (2311),   
   emergency-telephone-number-not-working     (2312),   
   traffic-lights-not-working                 (2313),   
   traffic-lights-working-incorrectly         (2314),   
   ramp-control-signals-not-working           (2315),   
   ramp-control-signals-working-incorrectly   (2316),   
   temporary-traffic-lights-not-working       (2317),   
   temporary-traffic-lights-working-incorrectly (2318),   
   traffic-signal-control-computer-not-working (2319),   
   traffic-signal-timings-changed             (2320),   
   overheight-warning-system-triggered        (2321),   
   equipment-failure                          (2322),   
   railroad-crossing-equipment-failure        (2323),   
   tunnel-ventilation-not-working             (2324),   
   power-failure                              (2325),   -- Hint: Use for localized cases
                                                        -- of power loss
   widespread-power-outages                   (2326),   -- Alternative  rendering:
                                                        -- widespread power cuts
   technical-problems                         (2327),   
   sign-down                                  (2328),   
   lines-in-road-faded                        (2329),   
   damaged-light-standard                     (2330),   -- Used for all forms of pole/
                                                        -- support damage
   traffic-signal-stuck-on-flash              (2331),   
   guide-rail                                 (2332),   -- Used for barriers as well
   fencing                                    (2333),   
   light-standard-hanging-by-wires            (2334),   
   call-box                                   (2335),   
   signal-cabinet                             (2336),   -- Use for all types of equipment
                                                        -- cabinets
   detector                                   (2337),   -- All forms of vehicle detectors
   improper-use-of-State-vehicle-or-equipment (2338),   
   bulb-out                                   (2339),   
   not-yet-operational                        (2340),   -- When installed but not yet
                                                        -- brought on-line for use by the
                                                        -- system
   not-yet-installed                          (2341),   -- When planned
   -- Cancel Types
   electronic-signs-repaired                  (2428),   
   emergency-call-facilities-restored         (2429),   
   traffic-signals-repaired                   (2430),   
   railroad-crossing-equipment-now-working-normally (2431),   
   -- Restrictions
   restrictions                               (2561),   
   ramp-restrictions                          (2562),   
   truck-restriction                          (2563),   
   speed-restriction                          (2564),   -- Used for required speeds, not
                                                        -- advised speeds
   noise-restriction                          (2565),   
   traffic-regulations-have-been-changed      (2566),   
   local-access-only                          (2567),   
   no-trailers                                (2568),   
   no-high-profile-vehicles                   (2569),   
   hazardous-materials-truck-restriction      (2570),   
   no-through-traffic                         (2571),   
   no-motor-vehicles                          (2572),   
   width-limit                                (2573),   -- Typically followed by a number
                                                        -- and unit value
   height-limit                               (2574),   -- Typically followed by a number
                                                        -- and unit value
   length-limit                               (2575),   -- Typically followed by a number
                                                        -- and unit value
   axle-load-limit                            (2576),   -- Typically followed by a number
                                                        -- and unit value
   gross-weight-limit                         (2577),   -- Typically followed by a number
                                                        -- and unit value
   axle-count-limit                           (2578),   -- Typically followed by a number
                                                        -- and unit value
   carpool-lane-available                     (2579),   
   carpool-restrictions-changed               (2580),   
   hOV-2-no-single-occupant-vehicles          (2581),   
   hOV-3-no-vehicles-with-less-than-three-occupants (2582),   
   bus-lane-available-for-all-vehicles        (2583),   
   truck-lane-available-for-all-vehicles      (2584),   
   permits-call-in-basis                      (2585),   
   permits-temporarily-closed                 (2586),   
   permits-closed                             (2587),   
   road-use-permits-required                  (2588),   
   -- Cancel Types
   permits-open                               (2675),   
   restrictions-for-high-profile-vehicles-lifted (2676),   
   width-limit-lifted                         (2677),   
   height-limit-lifted                        (2678),   
   length-limit-lifted                        (2679),   
   axle-load-limit-lifted                     (2680),   
   weight-limit-lifted                        (2681),   
   axle-count-limit-lifted                    (2682),   
   carpool-restrictions-lifted                (2683),   
   lane-restrictions-lifted                   (2684),   
   ramp-restrictions-lifted                   (2685),   
   motor-vehicle-restrictions-lifted          (2686),   
   restrictions-lifted                        (2687),   
   -- Incident Response Status
   unconfirmed-report                         (2817),   
   initial-response-en-route                  (2818),   
   follow-up-response-en-route                (2819),   
   initial-response-on-scene                  (2820),   
   follow-up-response-on-scene                (2821),   
   confirmed-report                           (2822),   
   scene-is-unsecured-at-this-time            (2823),   -- Caution: This has different
                                                        -- meanings in Public Safety use
   response-scene-secured                     (2824),   -- Caution: This has different
                                                        -- meanings in Public Safety use
   rescue-and-recovery-work-in-progress       (2825),   
   extraction-in-progress                     (2826),   
   clearance-work-in-progress                 (2827),   
   body-removal-operations                    (2828),   
   fire-containment-contained                 (2829),   
   fire-containment-not-contained             (2830),   
   event-cleared                              (2831),   -- Meaning that responder has
                                                        -- left scene, not that
                                                        -- surrounding traffic has
                                                        -- cleared to a normal level
   traffic-clearing                           (2832),   
   incident-closed                            (2833),   -- A "case closed" meaning which
                                                        -- can differ considerably by
                                                        -- local agency policies
   -- Disasters
   -- Water Related
   flash-flood                                (3073),   
   major-flood                                (3074),   
   reservoir-failure                          (3075),   
   levee-failure                              (3076),   
   tsunami                                    (3077),   
   tidal-wave                                 (3078),   
   -- Fire Related
   volcanic-eruption                          (3079),   
   ash-fall                                   (3080),   
   lava-flow                                  (3081),   
   serious-fire                               (3082),   
   forest-fire                                (3083),   
   wildfire                                   (3084),   
   building-fire                              (3085),   
   brush-fire                                 (3086),   
   grass-fire                                 (3087),   
   fire-danger-extreme                        (3088),   
   fire-danger-very-high                      (3089),   
   fire-danger-high                           (3090),   
   fire-danger-medium                         (3091),   
   fire-danger-low                            (3092),   
   --  Other
   earthquake-damage                          (3093),   
   air-crash                                  (3094),   
   rail-crash                                 (3095),   
   toxic-release                              (3096),   
   toxic-leak                                 (3097),   
   radioactive-release                        (3098),   
   radiation-hazard                           (3099),   
   reactor-leakage                            (3100),   
   explosion                                  (3101),   
   major-hazardous-materials-fire             (3102),   -- Alternative Rendering: Major
                                                        -- HAZMAT fire
   major-hazardous-materials-release          (3103),   -- Alternative Rendering: Major
                                                        -- HAZMAT release
   -- Cancel Types
   disaster-cleared                           (3199),   
   -- Disturbances
   assault                                    (3329),   -- This index is not to be used
                                                        -- as a default value for this
                                                        -- category
   crime                                      (3330),   
   robbery                                    (3331),   
   fare-dispute                               (3332),   
   shooting                                   (3333),   
   gunfire-on-roadway                         (3334),   
   suicide                                    (3335),   
   fight                                      (3336),   -- Involves a few  persons and is
                                                        -- localized (alt: brawl)
   gang-fight                                 (3337),   -- Multi-party event occurring
                                                        -- which may involve weapons
   person-harassment                          (3338),   -- "person" may be rendered as
                                                        -- "passenger" if used in a
                                                        -- controlled environment such as
                                                        -- transit
   person-injured                             (3339),   
   sick-customer                              (3363),   
   unruly-passenger                           (3340),   
   person-intoxicated                         (3341),   
   crowd-control-problem                      (3342),   
   demonstration                              (3343),   
   march                                      (3344),   
   public-disturbance                         (3345),   
   riot                                       (3346),   
   civil-unrest                               (3347),   
   civil-emergency                            (3348),   
   strike                                     (3349),   
   public-transit-strike                      (3350),   -- Hint: Strike affecting
                                                        -- services
   stampede                                   (3351),   
   teargas-used                               (3352),   
   security-alert                             (3353),   -- Heightened security procedures
                                                        -- in effect
   security-incident                          (3354),   
   checkpoint                                 (3355),   
   bomb-alert                                 (3356),   
   terrorist-incident                         (3357),   
   high-velocity-shell-fire                   (3358),   -- Hint: Used as a part of
                                                        -- avalanche control
   explosives-in-use                          (3359),   
   air-raid                                   (3360),   
   weapons-of-mass-destruction-threat         (3361),   
   military-operations                        (3362),   -- (war)
   -- Cancel Types
   security-problem-cleared                   (3454),   
   traffic-disturbance-cleared                (3455),   
   -- Sporting Events
   sports-event                               (3585),   
   game                                       (3586),   
   tournament                                 (3587),   
   track-and-field-event                      (3588),   
   baseball-game                              (3589),   
   basketball-game                            (3590),   
   boxing-match                               (3591),   
   football-game                              (3592),   
   soccer-game                                (3593),   
   golf-tournament                            (3594),   
   hockey-game                                (3595),   
   tennis-tournament                          (3596),   
   wrestling-match                            (3597),   
   road-race                                  (3598),   -- Hint: used for motorcycle
                                                        -- races as well
   automobile-race                            (3599),   
   bicycle-race                               (3600),   
   race-event                                 (3601),   
   marathon                                   (3602),   
   horse-show                                 (3603),   
   rodeo                                      (3604),   
   water-sports-event                         (3605),   
   winter-sports-event                        (3606),   
   skating-event                              (3607),   
   dog-sled-race                              (3608),   
   -- Cancel Types
   sporting-event-ended                       (3711),   
   -- Special Events
   major-event                                (3841),   
   airshow                                    (3842),   
   hot-air-ballooning                         (3843),   
   concert                                    (3844),   
   state-occasion                             (3845),   
   vIP-visit                                  (3846),   
   show                                       (3847),   
   festival                                   (3848),   -- Used for farmers' markets as
                                                        -- well
   exhibition                                 (3849),   
   performing-arts                            (3850),   
   outdoor-market                             (3851),   -- Used for farmers' markets as
                                                        -- well
   fair                                       (3852),   
   carnival                                   (3853),   
   fireworks-display                          (3854),   
   trade-expo                                 (3855),   
   movie-filming                              (3856),   
   presidential-visit                         (3857),   
   parade                                     (3858),   
   procession                                 (3859),   
   funeral-procession                         (3860),   
   crowd                                      (3861),   
   holiday-traffic-crowds                     (3862),   
   -- Cancel Types
   event-ended                                (3967),   
   -- Parking Information
   normal-parking-restrictions-lifted         (4097),   -- Hint: used when a PARKING
                                                        -- restriction is lifted
                                                        -- (overnight parking allowed
                                                        -- during event)  Not to be used
                                                        -- as a default for this category
   parking-meter-restrictions-lifted          (4098),   -- Hint: used when a METER
                                                        -- restriction is lifted (metered
                                                        -- parking free during event)
   special-parking-restrictions-in-force      (4099),   
   full-parking-lot                           (4100),   
   full-parking-garage                        (4101),   
   all-parking-lots-full                      (4102),   
   no-parking-spaces-available                (4103),   
   only-a-few-spaces-available                (4104),   
   spaces-available                           (4105),   -- Typically preceded by a #
                                                        -- value
   no-parking                                 (4106),   -- Typically followed by
                                                        -- restriction data
   parking-on-one-side-of-street-only         (4107),   
   parking-on-both-sides-of-street            (4108),   
   parallel-parking-only                      (4109),   
   parking-meters-not-available               (4110),   
   use-of-parking-meters-restricted           (4111),   
   event-parking                              (4112),   
   handicapped-parking                        (4113),   
   long-term-parking                          (4114),   
   overnight-parking                          (4115),   
   short-term-parking                         (4116),   
   parking-by-permit-only                     (4117),   
   emergency-parking-only                     (4118),   
   emergency-stopping-only                    (4119),   
   parking                                    (4120),   -- Typically followed by
                                                        -- restriction data
   stopping                                   (4121),   -- Typically followed by
                                                        -- restriction data
   standing                                   (4122),   -- Typically followed by
                                                        -- restriction data
   tow-away-zone                              (4123),   
   school-zone                                (4124),   -- Treat as Speed Limit,
                                                        -- with details to follow
   speed-zone                                 (4125),   -- Treat as Speed Limit,
                                                        -- with details to follow
   loading-zone                               (4126),   -- Typically followed by
                                                        -- restriction data
   state-law                                  (4127),   
   van-accessible                             (4128),   
   -- Cancel Types
   special-parking-restrictions-lifted        (4222),   
   no-parking-information-available           (4223),   
   -- Information System
   information-available-on-radio             (4353),   -- Not to be used as a default
                                                        -- for this category D12-1
   information-available-on-TV                (4354),   
   call-to-get-information                    (4355),   
   information-available-via-Internet         (4356),   
   test-message                               (4357),   -- Not to be displayed on
                                                        -- consumer devices if possible
   no-information-available                   (4358),   -- Typically combined with "on
                                                        -- xxx service" where xxx is a
                                                        -- type of service (bus, rail,
                                                        -- etc.)
   null-description                           (4359),   -- (but with event location or
                                                        -- other information provided in
                                                        -- the message)
   police-assistance                          (4361),   
   police-monitor-CB                          (4362),   -- D12-3
   emergency-notification                     (4363),   
   in-emergency-dial-911                      (4364),   -- D12-14
   travel-Info-call-511                       (4365),   -- D12-5
   car-pool-information                       (4366),   -- D12-2
   information-service-resumed                (4478),   
   -- Cancel Types
   information-service-is-being-suspended     (4360),   
   message-canceled                           (4479),   -- Not Recommended for use
   -- Weather Conditions
   -- General Weather
   overcast                                   (4609),   -- This index is not to be used
                                                        -- as a default value for this
                                                        -- category
   cloudy                                     (4610),   
   mostly-cloudy                              (4611),   
   partly-cloudy                              (4612),   
   partly-sunny                               (4613),   
   mostly-sunny                               (4614),   
   sunny                                      (4615),   
   fair-skies                                 (4616),   
   clear-skies                                (4617),   
   mostly-clear                               (4618),   
   mostly-dry                                 (4619),   
   dry                                        (4620),   
   uV-index-very-high                         (4621),   
   uV-index-high                              (4622),   
   uV-index-moderate                          (4623),   
   uV-index-low                               (4624),   
   uV-index-very-low                          (4625),   
   barometric-pressure                        (4626),   -- Typically followed by a number
                                                        -- and value
   ozone-alert                                (4627),   
   -- Lighting Types
   lighting-unknown                           (4628),   
   artificial-exterior-light                  (4629),   
   artificial-interior-light                  (4630),   
   darkness                                   (4631),   -- Also used when not lighted
   dusk                                       (4632),   
   dawn                                       (4633),   
   moonlight                                  (4634),   
   daylight                                   (4635),   
   -- Cancel Types
   weather-forecast-withdrawn                 (4735),   
   -- Precipitation
   severe-weather                             (4865),   
   blizzard                                   (4866),   
   heavy-snow                                 (4867),   
   snow                                       (4868),   
   light-snow                                 (4869),   
   snow-showers                               (4870),   
   winter-storm                               (4871),   
   ice-glaze                                  (4872),   
   heavy-frost                                (4873),   
   frost                                      (4874),   
   ice-storm                                  (4875),   
   sleet                                      (4876),   
   rain-and-snow-mixed                        (4877),   
   rain-changing-to-snow                      (4878),   
   damaging-hail                              (4879),   
   hail                                       (4880),   
   thunderstorms                              (4881),   
   thundershowers                             (4882),   
   extremely-heavy-downpour                   (4883),   
   heavy-rain                                 (4884),   
   rain                                       (4885),   
   light-rain                                 (4886),   
   drizzle                                    (4887),   
   showers                                    (4888),   
   dew                                        (4889),   
   -- Cancel Types
   precipitation-cleared                      (4991),   
   -- Winds
   tornado                                    (5121),   -- Note that this can be combined
                                                        -- with "alert" "warning" etc.
                                                        -- This index is not to be used
                                                        -- as a default value for this
                                                        -- category
   hurricane                                  (5122),   
   hurricane-force-winds                      (5123),   
   tropical-storm                             (5124),   
   gale-force-winds                           (5125),   
   storm-force-winds                          (5126),   
   strong-winds                               (5127),   
   moderate-winds                             (5128),   
   light-winds                                (5129),   
   calm                                       (5130),   
   gusty-winds                                (5131),   
   crosswinds                                 (5132),   
   windy                                      (5133),   
   -- Cancel Types
   strong-winds-have-eased                    (5246),   
   strong-wind-forecast-withdrawn             (5247),   
   -- Visibility & Air Quality
   -- Visibility
   dense-fog                                  (5377),   -- This index is not to be used
                                                        -- as a default value for this
                                                        -- category
   fog                                        (5378),   
   patchy-fog                                 (5379),   
   freezing-fog                               (5380),   
   ice-fog                                    (5405),   -- Different than freezing fog,
                                                        -- ice fog occurs well below
                                                        -- freezing temps and is quite
                                                        -- common in the Fairbanks area.
   mist                                       (5381),   
   haze                                       (5382),   
   visibility-reduced                         (5383),   
   visibility-blocked                         (5404),   -- Used when signs, trees, etc.,
                                                        -- block the view
   white-out                                  (5384),   -- Alternative Rendering: Snow
                                                        -- glare
   blowing-snow                               (5385),   
   smoke-hazard                               (5386),   
   spray-hazard                               (5387),   
   low-sun-glare                              (5388),   -- Do not use for snow glare
   snow-glare                                 (5389),   
   blowing-dust                               (5390),   
   blowing-sand                               (5391),   -- Hint: dune accumulations
   dust-storms                                (5392),   
   sandstorms                                 (5393),   
   -- Air Quality
   air-quality-good                           (5394),   
   air-quality-fair                           (5395),   
   air-quality-poor                           (5396),   
   air-quality-very-poor                      (5397),   
   severe-exhaust-pollution                   (5398),   
   smog-alert                                 (5399),   
   pollen-count-high                          (5400),   
   pollen-count-medium                        (5401),   
   pollen-count-low                           (5402),   
   swarms-of-insects                          (5403),   
   -- Cancel Types
   fog-clearing                               (5499),   
   visibility-improved                        (5500),   
   fog-forecast-withdrawn                     (5501),   
   pollution-alert-ended                      (5502),   
   air-quality-improved                       (5503),   
   -- Temperature
   maximum-temperature                        (5633),   -- This index is not to be used
                                                        -- as a default value for this
                                                        -- category
   temperature                                (5634),   -- Typically followed by a number
                                                        -- value and a unit value
   minimum-temperature                        (5635),   
   current-temperature                        (5636),   
   heat-index                                 (5637),   
   extreme-heat                               (5638),   
   hot                                        (5639),   
   hotter                                     (5640),   
   heat                                       (5641),   
   warmer                                     (5642),   
   warm                                       (5643),   
   mild                                       (5644),   
   cool                                       (5645),   
   cooler                                     (5646),   
   cold                                       (5647),   
   colder                                     (5648),   
   very-cold                                  (5649),   
   extreme-cold                               (5650),   
   wind-chill                                 (5651),   
   dewpoint                                   (5652),   
   relative-humidity                          (5653),   
   -- Cancel Types
   temperatures-close-to-the-seasonal-norm    (5758),   
   less-extreme-temperatures                  (5759),   
   -- Pavement Conditions
   -- General
   impassable                                 (5889),   
   almost-impassable                          (5890),   
   passable-with-care                         (5891),   
   passable                                   (5892),   
   surface-water-hazard                       (5893),   
   danger-of-hydroplaning                     (5894),   
   wet-pavement                               (5895),   
   treated-pavement                           (5896),   -- Alternative Rendering:
                                                        -- chemical wet
   slippery                                   (5897),   
   low-ground-clearance                       (5938),   -- Use for W12-2 types
   at-grade-level-crossing                    (5937),   
   -- On Roadway items
   mud-on-roadway                             (5898),   
   leaves-on-roadway                          (5899),   
   loose-sand-on-roadway                      (5900),   
   loose-gravel                               (5901),   
   fuel-on-roadway                            (5902),   
   oil-on-roadway                             (5903),   
   road-surface-in-poor-condition             (5904),   
   melting-tar                                (5905),   
   uneven-lanes                               (5935),   
   rough-road                                 (5931),   
   rough-crossing                             (5936),   -- Typically used with grade
                                                        -- crossings at rails
   -- Ice & Snow
   ice                                        (5906),   
   icy-patches                                (5907),   
   black-ice                                  (5908),   
   ice-pellets-on-roadway                     (5909),   
   ice-build-up                               (5910),   
   freezing-rain                              (5911),   
   wet-and-icy-roads                          (5912),   
   slush                                      (5914),   
   melting-snow                               (5913),   
   frozen-slush                               (5915),   
   snow-on-roadway                            (5916),   
   packed-snow                                (5917),   
   packed-snow-patches                        (5918),   
   plowed-snow                                (5919),   
   wet-snow                                   (5920),   
   fresh-snow                                 (5921),   
   powder-snow                                (5922),   
   granular-snow                              (5923),   
   frozen-snow                                (5924),   
   crusted-snow                               (5925),   
   deep-snow                                  (5926),   
   snow-drifts                                (5927),   
   drifting-snow                              (5928),   
   expected-snow-accumulation                 (5929),   
   current-snow-accumulation                  (5930),   
   -- Road Surface
   sand                                       (5932),   -- Can use for W7-4d
   gravel                                     (5933),   -- Can use for W7-4e
   paved                                      (5934),   -- Can use for W7-4f
   -- Cancel Types
   dry-pavement                               (6011),   
   snow-cleared                               (6012),   
   pavement-conditions-improved               (6013),   
   skid-hazard-reduced                        (6014),   
   pavement-conditions-cleared                (6015),   
   -- Winter Driving Restrictions and Recommendations
   winter-equipment-recommended               (6145),   
   winter-equipment-required                  (6146),   
   snow-chains-recommended                    (6147),   
   snow-chains-required                       (6148),   
   snow-chains-prohibited                     (6149),   
   studded-tires-prohibited                   (6150),   
   snow-tires-recommended                     (6151),   
   snow-tires-required                        (6152),   
   four-wheel-drive-recommended               (6153),   
   four-wheel-drive-required                  (6154),   
   snow-tires-or-chains-recommended           (6155),   
   snow-tires-or-chains-required              (6156),   
   -- Cancel Types
   winter-driving-requirements-lifted         (6271),   -- In early editions this was
                                                        -- incorrectly listed as code
                                                        -- 6157
   -- Winter Driving Index
   driving-conditions-good                    (6401),   
   driving-conditions-fair                    (6402),   
   difficult-driving-conditions               (6403),   
   very-difficult-driving-conditions          (6404),   
   hazardous-driving-conditions               (6405),   
   extremely-hazardous-driving-conditions     (6406),   
   -- Suggestion Advice
   why-not-ride-share                         (6657),   
   is-this-your-no-ride-day                   (6658),   
   why-not-use-transit                        (6659),   
   why-not-park-and-ride                      (6660),   
   why-not-try-paratransit                    (6661),   
   why-not-travel-by-rail                     (6662),   
   why-not-use-the-subway                     (6663),   
   why-not-try-rapid-transit                  (6664),   
   why-not-travel-by-bus                      (6665),   
   your-parking-ticket-covers-the-return-ride (6666),   
   avoid-the-rush-hour                        (6667),   
   do-not-allow-unnecessary-gaps              (6668),   
   follow-the-vehicle-in-front-smoothly       (6669),   
   do-not-slow-down-unnecessarily             (6670),   
   watch-for-muggers                          (6671),   
   watch-for-pickpockets                      (6672),   
   watch-for-thieves                          (6673),   
   sorry-for-any-delay                        (6674),   
   thank-you-for-your-understanding           (6675),   
   we-appreciate-your-patience                (6676),   
   we-are-grateful-for-your-cooperation       (6677),   
   share-the-road                             (6678),   
   -- Warning Advice
   risk                                       (6913),   -- Conditions are more likely
                                                        -- than "normal"
   watch                                      (6914),   -- Conditions are favorable for
                                                        -- an event to occur
   warning                                    (6915),   -- An event has occurred but is
                                                        -- not (yet) near
   alert                                      (6916),   -- An event has occurred and it
                                                        -- is near
   danger                                     (6917),   
   danger-of-explosion                        (6918),   
   danger-of-fire                             (6919),   
   extra-police-patrols-in-operation          (6920),   
   look-out-for-vehicles-stopped-under-bridges (6921),   
   increased-risk-of-accident                 (6922),   
   rescue-and-recovery-work-in-progress-at-sceneREMOVED (6923),   -- No long used, see item 2825
   police-at-scene                            (6924),   
   emergency-vehicles-at-scene                (6925),   
   traffic-being-directed-around-accident-area (6926),   
   police-directing-traffic                   (6927),   
   rescue-workers-directing-traffic           (6928),   
   repairs-in-progress                        (6929),   
   pilot-car-in-operation                     (6930),   
   look-out-for-flagger                       (6931),   -- Alternative Rendering: look
                                                        -- out for flagman
   look-out-for-workers                       (6952),   -- Alternative Rendering:
                                                        -- workers
   police-checks-in-operation                 (6932),   -- Hint: all types of checks
   truck-check-point                          (6937),   
   lockdown                                   (6935),   
   security-check-point                       (6936),   
   single-occupancy-vehicle-check-point       (6938),   
   mandatory-speed-limit-in-force             (6933),   
   speed-limit-in-force-for-heavy-vehicles    (6934),   
   behind-you                                 (6950),   
   ride-with-traffic                          (6953),   
   prepare-to-evacuate-area                   (6954),
   avoid                                      (6955),  
   -- MUTCD Signs
   look                                       (6939),   
   photo-enforced                             (6940),   
   traffic-signs                              (6951),   
   traffic-laws                               (6941),   
   use-low-gear                               (6942),   
   bridge-ices-before-road                    (6943),   
   speed-checked-by-radar                     (6944),   
   speed-checked-by-aircraft                  (6945),   
   fines                                      (6946),   
   fines-higher                               (6947),   
   fines-doubled                              (6948),   
   fines-tripled                              (6949),   
   -- Cancel Types
   evacuation-canceled                        (7033),  
   warning-canceled                           (7034),   -- Canceling a warning may
                                                        -- "revert" to a watch
   watch-canceled                             (7035),   
   alert-canceled                             (7036),   -- Canceling an alert may
                                                        -- "revert" to a warning
   ended                                      (7037),   -- Hint: used for many sporting/
                                                        -- special events
   cleared                                    (7038),   
   canceled                                   (7039),   
   -- Instructions (Recommendations)
   drive-carefully                            (7169),   
   drive-with-extreme-caution                 (7170),   
   approach-with-care                         (7171),   
   keep-your-distance                         (7172),   
   increase-normal-following-distance         (7173),   
   test-your-brakes                           (7174),   
   cross-intersection-with-care               (7175),   
   pass-with-care                             (7176),   -- Use as MUTCD sign
   pass                                       (7200),   -- Used for passing action,
                                                        -- as in do not pass
   use-low-beam-headlights                    (7177),   
   use-fog-lights                             (7178),   
   use-hazard-warning-lights                  (7179),   -- Alternative Rendering: use
                                                        -- blinkers
   do-not-leave-your-vehicle                  (7180),   
   leave-your-vehicle-and-proceed-to-next-safe-place (7181),   
   turn-off-engine                            (7182),   -- Alternative Rendering: switch
                                                        -- off engine
   close-all-windows-turn-off-heater-air-conditioner-and-vents (7183),   
   turn-off-air-conditioner-to-prevent-engine-overheating (7184),   
   turn-off-mobile-phones-and-two-way-radios  (7185),   -- Alternative Rendering: switch
                                                        -- off mobile phones and two way
                                                        -- radios
   prepare-to-stop                            (7186),   
   be-prepared-to-stop                        (7201),   
   stop-at-next-rest-area                     (7187),   
   stop-at-next-safe-place                    (7188),   
   only-travel-if-absolutely-necessary        (7189),   
   drive-to-another-service-area              (7190),   
   use-through-traffic-lanes                  (7191),   
   use-local-traffic-lanes                    (7192),   
   use-left-hand-parallel-roadway             (7193),   
   use-right-hand-parallel-roadway            (7194),   
   use-heavy-vehicle-lane                     (7195),   -- Alternative Rendering: use
                                                        -- truck lanes
   observe-recommended-speed                  (7196),   
   signals-sequenced-for-speed                (7202),   -- Typically followed by speed
   maintain-top-safe-speed                    (7203),   
   facing-traffic                             (7197),   
   push-button                                (7198),   
   to-cross-street                            (7199),   
   evacuate-area-voluntarily                  (7204),  
   shelter-in-place                           (7205),  
   -- Instructions (Mandatory)
   keep-to-the-right                          (7425),   
   keep-to-the-left                           (7426),   
   use-right-lane                             (7427),   
   use-left-lane                              (7428),   
   stay-in-lane                               (7450),   
   merge                                      (7451),   -- Typically followed by
                                                        -- direction left/right Used for
                                                        -- W4-1R and W4-1L
   heavy-vehicles-use-right-lane              (7429),   
   heavy-vehicles-use-left-lane               (7430),   
   observe-signals                            (7431),   
   observe-signs                              (7432),   
   no-passing                                 (7433),   -- Used for MUTCD signs
   no-smoking                                 (7434),   
   no-open-flames                             (7435),   
   use-shoulder-as-lane                       (7436),   
   do-not-drive-on-the-shoulder               (7437),   
   allow-emergency-vehicles-to-pass           (7438),   
   clear-a-lane-for-emergency-vehicles        (7439),   
   pull-over-to-the-edge-of-the-roadway       (7440),   
   wait-for-escort-vehicle                    (7441),   
   in-emergency-wait-for-police-patrol        (7442),   
   reduce-your-speed                          (7443),   
   observe-speed-limits                       (7444),   
   check-point                                (7445),   
   entry-requirements                         (7446),   
   insurance-requirements                     (7447),   
   firearms-requirements                      (7448),   
   pet-requirements                           (7449),   
   slower-traffic-keep-right                  (7452),   
   keep-off                                   (7453),   -- Typically followed by
                                                        -- object
   evacuate-area-immediately                  (7454),
   -- Cancel Types
   shoulder-travel-no-longer-allowed          (7547),   
   -- Qualifiers
   -- Locations
   above                                      (7681),   -- Not to be used as the default
                                                        -- for this category
   below                                      (7682),   
   in                                         (7683),   
   around                                     (7684),   
   after                                      (7685),   
   before                                     (7686),   
   at                                         (7687),   -- Hint: used in conjunction with
                                                        -- generic locations
   on                                         (7688),   -- Hint: used in conjunction with
                                                        -- "roadway" or other terms for
                                                        -- both places (on-shoulder) and
                                                        -- events (on-green)
   near                                       (7689),   -- Hint: used with generic
                                                        -- locations and lanes
   from-the                                   (7690),   
   terminal                                   (7691),   
   -- Weather Related
   falling-slowly                             (7692),   
   falling                                    (7693),   
   falling-quickly                            (7694),   
   rising-slowly                              (7695),   
   rising                                     (7696),   
   rising-quickly                             (7697),   
   steady                                     (7698),   
   likely                                     (7699),   
   changing-to                                (7700),   
   mostly                                     (7701),   
   partly                                     (7702),   
   minus                                      (7703),   
   weather-ended                              (7704),   
   expected                                   (7705),   
   low                                        (7706),   -- Typically used in
                                                        -- temperatures. See also "upper"
   mid                                        (7707),   
   high                                       (7708),   
   upper                                      (7709),   -- Typically used in temperatures or broad regions. 
                                                        -- See also Ã¢â‚¬Å“lowÃ¢â‚¬Â?, Ã¢â‚¬Â?midÃ¢â‚¬Â?, Ã¢â‚¬Å“highÃ¢â‚¬Â?, Ã¢â‚¬Å“middleÃ¢â‚¬Â?
   middle                                     (7765),  -- Typically used for broad regions
                                                       -- See also Ã¢â‚¬Å“upperÃ¢â‚¬Â?, Ã¢â‚¬Å“lowerÃ¢â‚¬Â?
   lower                                      (7764),  -- Typically used for broad regions
                                                       -- See also Ã¢â‚¬Å“upperÃ¢â‚¬Â?, Ã¢â‚¬Å“middleÃ¢â‚¬Â?
   unseasonably                               (7710),   
   reported                                   (7711),   
   -- Instructions
   advice                                     (7712),   
   due-to                                     (7713),   
   proceed-to                                 (7714),   
   transferred-to                             (7715),   
   use                                        (7716),   
   -- Prepositional Use
   affecting                                  (7717),   
   blocking                                   (7718),   
   connecting                                 (7719),   
   finished                                   (7720),   -- Alt term: finish
   for                                        (7721),   
   or                                         (7722),   
   -- Other
   and                                        (7723),   
   later                                      (7724),   
   level                                      (7725),   
   shortly                                    (7726),   
   soon                                       (7727),   
   service                                    (7728),   
   graffiti                                   (7733),   
   damaged                                    (7729),   
   out-of-order                               (7730),   -- See Asset Status items as well
   on-State-right-of-way                      (7732),   
   found-property                             (7734),   
   vandalism                                  (7731),   
   major                                      (7766),  
   minor                                      (7767),  
   -- MUTCD Sign Usage
   begin-time                                 (7735),   -- Typically followed by a
                                                        -- value entry and a time entry
                                                        -- (AM/PM)
   added                                      (7736),   -- Typically preceded by an
                                                        -- object entry
   end-time                                   (7737),   -- Typically followed by a
                                                        -- value entry and a time entry
                                                        -- (AM/PM)
   no                                         (7738),   -- Typically followed by a
                                                        -- value entry and any day/time
                                                        -- limits
   do-not                                     (7739),   -- Also used for "does not"
   block                                      (7740),   -- Also used for blocks
   except                                     (7741),   -- Typically followed by a
                                                        -- value entry and a day/time
                                                        -- entry
   day                                        (7742),   -- Alt: daytime, daylight
                                                        -- hours
   night                                      (7743),   -- Alt: night time, night
                                                        -- time hours
   any-time                                   (7744),   -- Used also for "allowed"
   has                                        (7745),   -- As in: has green (alt
                                                        -- form: with)
   must                                       (7757),   -- As in: <lane> must <turn>
   may-have                                   (7746),   -- As in: may have green
   may-exceed                                 (7759),   -- As in: may exceed 80 mph
   only                                       (7747),   
   lifted                                     (7748),   -- As in gate lifted
   empty                                      (7749),   
   turning                                    (7750),   -- Used also for turns or
                                                        -- turn
   u-turn                                     (7751),   -- As in no u-turn allowed
   wait-for                                   (7752),   
   when-flashing                              (7753),   
   duration                                   (7754),   -- Typically followed by a
                                                        -- value entry and a time entry
                                                        -- (Days/Hours/Min)
   cross                                      (7755),   
   when-wet                                   (7756),   
   oncoming                                   (7758),   -- Typically followed by
                                                        -- object or vehicle types
   to-request                                 (7760),   -- As in to request X do Y
   exempt                                     (7761),   
   skewed                                     (7762),   
   when-children-are-present                  (7763),   -- Use for S4-2
   -- Generic Locations
   -- Road Related
   on-bridges                                 (7937),   -- Not to be used as the default
                                                        -- for this category
   in-tunnels                                 (7938),   
   entering-or-leaving-tunnels                (7939),   
   on-ramps                                   (7940),   
   in-road-construction-area                  (7941),   
   around-a-curve                             (7942),   
   on-curve                                   (8026),   
   on-tracks                                  (8009),   
   in-street                                  (8025),   -- As in in-street pad
                                                        -- crossing
   shoulder                                   (8027),   
   on-minor-roads                             (7943),   
   in-the-opposing-lanes                      (7944),   
   adjacent-to-roadway                        (7945),   
   across-tracks                              (8024),   
   on-bend                                    (7946),   
   intersection                               (8032),   
   entire-intersection                        (7947),   
   in-the-median                              (7948),   
   moved-to-side-of-road                      (7949),   
   moved-to-shoulder                          (7950),   
   on-the-roadway                             (7951),   -- Use generic locations and
                                                        -- groups affected to make other
                                                        -- such phrases
   dip                                        (8010),   --
   traffic-circle                             (8011),   -- Used for W2-6 graphic as
                                                        -- well. Alt term: roundabout
   crossover                                  (8028),   
   cross-road                                 (8029),   -- Also used for W2-1 Note
                                                        -- that in some uses this is one
                                                        -- word
   side-road                                  (8030),   -- Do not used for W2-2R and
                                                        -- W2-2L
   to                                         (8014),   
   by                                         (8015),   
   through                                    (8016),   
   area-of                                    (8017),   -- Also area
   under                                      (8018),   
   over                                       (8019),   
   from                                       (8020),   
   approaching                                (8021),   
   entering-at                                (8022),   -- Alt form: Entrance
   exiting-at                                 (8023),   
   -- Terrain & Geography
   in-shaded-areas                            (7952),   
   in-low-lying-areas                         (7953),   
   in-the-downtown-area                       (7954),   
   in-the-inner-city-area                     (7955),   
   in-parts                                   (7956),   
   in-some-places                             (7957),   
   in-the-ditch                               (7958),   
   in-the-valley                              (7959),   
   on-hill-top                                (7960),   
   near-the-foothills                         (7961),   
   at-high-altitudes                          (7962),   
   near-the-lake                              (7963),   
   near-the-shore                             (7964),   
   nearby-basin                               (8008),   
   over-the-crest-of-a-hill                   (7965),   
   other-than-on-the-roadway                  (7966),   
   near-the-beach                             (7967),   
   near-beach-access-point                    (7968),   
   mountain-pass                              (8006),   
   lower-level                                (7969),   
   upper-level                                (7970),   
   coast                                      (8034),  
   -- Transit Travel, Air Travel and Places
   airport                                    (7971),   
   concourse                                  (7972),   
   gate                                       (7973),   
   baggage-claim                              (7974),   
   customs-point                              (7975),   
   reservation-center                         (8007),   
   station                                    (7976),   
   platform                                   (7977),   -- Alternative Rendering: track
   dock                                       (7978),   
   depot                                      (7979),   
   ev-charging-point                          (7980),   
   information-welcome-point                  (7981),   -- Use for Tourist Information as
                                                        -- well (D9-10)
   at-rest-area                               (7982),   
   at-service-area                            (7983),   
   at-weigh-station                           (7984),   
   roadside-park                              (8033),   
   picnic-areas                               (7985),   
   rest-area                                  (7986),   
   service-stations                           (7987),   
   toilets                                    (7988),   -- Note also rest rooms in
                                                        -- structures
   bus-stop                                   (8031),   
   park-and-ride-lot                          (8012),   -- Not to be used as a mode
                                                        -- of travel
   -- Direction of Travel
   on-the-right                               (7989),   
   on-the-left                                (7990),   
   in-the-center                              (7991),   
   in-the-opposite-direction                  (7992),   
   cross-traffic                              (7993),   
   northbound-traffic                         (7994),   
   eastbound-traffic                          (7995),   
   southbound-traffic                         (7996),   
   westbound-traffic                          (7997),   
   -- Compass Points
   north                                      (7998),   
   south                                      (7999),   
   east                                       (8000),   
   west                                       (8001),   
   northeast                                  (8002),   
   northwest                                  (8003),   
   southeast                                  (8004),   
   southwest                                  (8005),   
   -- Lane/Roadway Descriptions
   -- Lanes
   all-roadways                               (8193),   -- Used as the default value
   through-lanes                              (8194),   
   left-lane                                  (8195),   
   right-lane                                 (8196),   
   center-lane                                (8197),   
   middle-lanes                               (8198),   
   middle-two-lanes                           (8199),   
   right-turning-lanes                        (8200),   
   left-turning-lanes                         (8201),   
   upper-deck-lanes                           (8236),   
   lower-deck-lanes                           (8237),   
   reversible-lanes                           (8238),   
   right-exit-lanes                           (8239),   
   left-exit-lanes                            (8240),   
   right-merging-lanes                        (8241),   
   left-merging-lanes                         (8242),   
   -- Ramps
   right-exit-ramp                            (8202),   
   right-second-exit-ramp                     (8243),   
   right-entrance-ramp                        (8203),   
   right-second-entrance-ramp                 (8245),   
   left-exit-ramp                             (8204),   
   left-second-exit-ramp                      (8244),   
   left-entrance-ramp                         (8205),   
   left-second-entrance-ramp                  (8246),   
   escape-ramp                                (8234),   -- A truck feature on steep
                                                        -- downgrades common in both
                                                        -- Alaska and elsewhere.
   -- Shoulders
   hard-shoulder                              (8206),   
   soft-shoulder                              (8207),   
   right-shoulder                             (8208),   
   left-shoulder                              (8209),   
   median                                     (8252),   
   sidewalk                                   (8251),   
   -- Other
   highways                                   (8235),   
   right-hand-parallel-lanes                  (8210),   -- Alternative Rendering:
                                                        -- right-hand frontage road
   left-hand-parallel-lanes                   (8211),   -- Alternative Rendering:
                                                        -- left-hand frontage road
   connecting-lanes                           (8212),   
   express-lanes                              (8213),   
   local-lanes                                (8214),   
   toll-lanes                                 (8215),   
   electronic-toll-lanes                      (8216),   
   toll-plaza                                 (8217),   
   inspection-lane                            (8218),   -- Alternative Rendering: Border
                                                        -- patrol inspection lane
   hOV-lanes                                  (8219),   -- Use when 2+ or 3+ is unknown
                                                        -- and for HOV in general
   bus-lanes                                  (8220),   
   carpool-lanes                              (8221),   
   truck-lanes                                (8222),   
   emergency-lanes                            (8223),   
   passing-lanes                              (8224),   
   climbing-lanes                             (8225),   
   slow-lane                                  (8226),   -- Alternative Rendering:
                                                        -- Crawler lane
   service-road                               (8227),   -- Alternative Rendering:
                                                        -- Frontage Road
   cycle-lane                                 (8228),   -- Use for bicycle lanes of all
                                                        -- types
   tracks                                     (8250),   -- Use for light rail and
                                                        -- transit uses, may have count
                                                        -- of tracks
   -- Bridges, Tunnels
   bridge                                     (8229),   
   overpass                                   (8230),   
   elevated-lanes                             (8231),   
   underpass                                  (8232),   
   tunnel                                     (8233),   -- Use for RG-200
   -- Lanes Groups
   all-exit-lanes                             (8247),   
   all-entry-lanes                            (8248),   
   either-shoulder                            (8249),   
   shoulder-work                              (8253),   -- Use for W21-5 as well
   -- Alternate Route
   detour-where-possible                      (8449),   
   no-detour-available                        (8450),   
   follow-signs                               (8451),   
   follow-detour-signs                        (8452),   
   follow-special-detour-markers              (8453),   
   do-not-follow-detour-signs                 (8454),   
   detour-in-operation                        (8455),   
   follow-local-detour                        (8456),   
   compulsory-detour-in-operation             (8457),   
   no-suitable-detour-available               (8458),   
   detour-is-no-longer-recommended            (8459),   
   local-drivers-are-recommended-to-avoid-the-area (8460),   
   trucks-are-recommended-to-avoid-the-area   (8461),   
   consider-alternate-route                   (8462),   
   consider-alternate-parking                 (8463),   
   consider-alternate-destination             (8464),   
   consider-alternate-area                    (8465),   
   -- Specific Route Types
   snow-route                                 (8466),   
   emergency-snow-route                       (8467),   
   evacuation-route                           (8468),   -- May be preceded by a
                                                        -- specific type, Used also for
                                                        -- general emergency routes.
   truck-route                                (8469),   
   hazardous-materials-route                  (8470),   -- May be used with 'any
                                                        -- time' for allowed, or 'no' for
                                                        -- prohibited, or 'detour'
   detour                                     (8471),   
   -- Unit Values
   -- Areas,  Distances  &  Speeds
   square-feet                                (8705),   
   square-meters                              (8706),   
   acres                                      (8707),   
   hectares                                   (8708),   
   inches                                     (8709),   
   feet                                       (8710),   
   mile                                       (8711),   -- Hint: used for offset as in
                                                        -- "at mile 123"  Alternative
                                                        -- Rendering: milepost marker
   miles                                      (8712),   -- Hint: Used for distance, as in
                                                        -- "ending 5 miles"
   nautical-miles                             (8713),   
   millimeters                                (8714),   
   meters                                     (8715),   
   kilometer                                  (8716),   -- Hint: used for offset as in
                                                        -- "at kilometer 123"
   kilometers                                 (8717),   
   feet-per-second                            (8718),   
   meters-per-second                          (8719),   
   mPH                                        (8720),   
   kPH                                        (8721),   
   knots                                      (8722),   
   elevation                                  (8766),   -- Typically followed by
                                                        -- value and units
   -- Times,  Days  &  Dates
   aM                                         (8723),   -- Both a time value and a radio
                                                        -- band value. A number value
                                                        -- may PRECEDE the unit value
                                                        -- used in representing the
                                                        -- frequency of a radio station
   pM                                         (8724),   
   holiday                                    (8726),   
   seconds                                    (8727),   
   minutes                                    (8728),   
   hours                                      (8729),   
   days                                       (8730),   -- Hint: useful for events
                                                        -- occurring for at least 24
                                                        -- hours
   weeks                                      (8731),   
   months                                     (8732),   
   other-times                                (8767),   -- Typically used to
                                                        -- represent a "default" allowed
                                                        -- condition
   -- Days of the Week
   nSunday                                    (8758),   
   nMonday                                    (8759),   
   nTuesday                                   (8760),   
   nWednesday                                 (8761),   
   nThursday                                  (8762),   
   nFriday                                    (8763),   
   nSaturday                                  (8764),   
   weekdays                                   (8765),   -- Alt text: Mon-Fri
   weekends                                   (8725),   -- In general date/time values
                                                        -- can be better coded in other
                                                        -- ways in most message sets
   -- Temps, Weights, Masses and Measurements
   degrees-Angle                               (8733),   -- Used for latitude, longitude
                                                        -- and bearing measured clockwise
                                                        -- from North
   degrees-Celsius                            (8734),   -- Alternate renderings possible
   degrees-Fahrenheit                         (8735),   -- Alternate renderings possible
   grams                                      (8736),   
   kilograms                                  (8737),   -- Also called a metric ton
                                                        -- (1000kg or ~2204 lbs)
   ounces                                     (8738),   
   pounds                                     (8739),   
   tons                                       (8740),   -- English Units (2000 lbs = 1
                                                        -- ton)
   fluid-ounces                               (8741),   
   gallons                                    (8742),   
   milliliters                                (8743),   
   liters                                     (8744),   
   kilograms-per-lane-mile                    (8745),   
   tons-per-lane-mile                         (8746),   
   -- Misc.
   dollar                                     (8747),   -- Alternative rendering: dollar
                                                        -- symbol  Not to be used as the
                                                        -- default value for this
                                                        -- category
   percent                                    (8748),   -- Alternative rendering: percent
                                                        -- symbol
   grade                                      (8757),   -- Typically preceded by a
                                                        -- percent value entry
   time-delimiter                             (8749),   -- Alternative rendering: "-"
   dollars                                    (8750),   -- Alternative rendering can use
                                                        -- local currency sign
   flight-number                              (8751),   -- A number value may PRECEDE the
                                                        -- unit value in use
   person-people                              (8752),   
   response-plan                              (8753),   -- A value may PRECEDE the unit
                                                        -- value in use (involving a
                                                        -- combination of numbers and/
                                                        -- or letters)
   placard-type                               (8754),   -- For hazmat class and division
                                                        -- type designations, a value may
                                                        -- PRECEDE the unit value in use
   placard-number                             (8755),   -- For chemical designations, a
                                                        -- value may PRECEDE the unit
                                                        -- value in use
   fM                                         (8756),   -- A number value may PRECEDE the
                                                        -- unit value in use representing
                                                        -- the frequency of a radio
                                                        -- station
   -- Transit Mode
   travel                                     (8961),   -- Hint: may include all modes
   transit                                    (8962),   -- Hint: may include all public
                                                        -- transit modes
   bus                                        (8963),   
   trolleybus                                 (8964),   
   rail                                       (8965),   
   commuter-rail                              (8966),   
   subway                                     (8967),   
   rapid-transit                              (8968),   
   light-rail                                 (8969),   
   streetcar                                  (8970),   -- Alternative Rendering: tram
   dial-a-ride                                (8971),   -- Alternative Rendering: demand
                                                        -- responsive transit
   park-and-ride                              (8972),   -- Not to be used as a place
   shuttle                                    (8973),   
   free-shuttle                               (8974),   -- Alternative Rendering: tram
   airport-shuttle                            (8975),   
   taxies                                     (8976),   
   ferry                                      (8977),   
   passenger-ferry                            (8978),   
   vehicle-ferry                              (8979),   
   aerial-tramway                             (8980),   
   automated-guideway                         (8981),   -- Include all types of guideways
   cable-cars                                 (8982),   
   monorail                                   (8983),   
   air-travel                                 (8984),   -- All modes of air travel
   hitch-hitching                             (8985),   
   walk                                       (8986),   -- Alt form: Walking
   -- Vehicle Groups Affected
   all-vehicles                               (9217),   
   bicycles                                   (9218),   
   motorcycles                                (9219),   -- to include mopeds as well
   cars                                       (9220),   -- (remapped from ERM value of
                                                        -- zero)
   light-vehicles                             (9221),   
   cars-and-light-vehicles                    (9222),   
   cars-with-trailers                         (9223),   
   cars-with-recreational-trailers            (9224),   
   vehicles-with-trailers                     (9225),   
   heavy-vehicles                             (9226),   
   trucks                                     (9227),   -- Use for RG-190
   buses                                      (9228),   
   articulated-buses                          (9229),   
   school-buses                               (9230),   
   vehicles-with-semi-trailers                (9231),   
   vehicles-with-double-trailers              (9232),   -- Alternative Rendering:
                                                        -- western doubles
   high-profile-vehicles                      (9233),   
   wide-vehicles                              (9234),   
   long-vehicles                              (9235),   
   hazardous-loads                            (9236),   
   exceptional-loads                          (9237),   
   abnormal-loads                             (9238),   
   convoys                                    (9239),   
   maintenance-vehicles                       (9240),   
   delivery-vehicles                          (9241),   
   vehicles-with-even-numbered-license-plates (9242),   
   vehicles-with-odd-numbered-license-plates  (9243),   
   vehicles-with-parking-permits              (9244),   
   vehicles-with-catalytic-converters         (9245),   
   vehicles-without-catalytic-converters      (9246),   
   gas-powered-vehicles                       (9247),   
   diesel-powered-vehicles                    (9248),   
   lPG-vehicles                               (9249),   
   military-convoys                           (9250),   
   military-vehicles                          (9251),   
   electric-powered-vehicles                  (9252),   
   hybrid-powered-vehicles                    (9253),   
   inherently-low-emission-vehicles            (9254),   
   commercial-vehicles                        (9255),   
   runaway-vehicles                           (9256),   
   vehicles-with-lugs                         (9257),   
   motor-driven-cycles                        (9258),   
   recreational-vehicles                      (9259),   -- Use for RVs
   non-motorized-vehicles                     (9260),   
   traffic                                    (9261),   -- Refers to all types of
                                                        -- motor traffic, all groups
   -- Traveler Group Affected
   through-traffic                            (9473),   
   holiday-traffic                            (9474),   
   residents                                  (9475),   
   visitors                                   (9476),   
   long-distance-traffic                      (9477),   
   local-traffic                              (9478),   
   regional-traffic                           (9479),   
   arrivals                                   (9480),   
   departures                                 (9481),   
   airline-travelers                          (9482),   
   commuter-airline-travelers                 (9483),   
   domestic-airline-travelers                 (9484),   
   international-airline-travelers            (9485),   
   pedestrians                                (9486),   
   bicyclists                                 (9487),   -- Hint: may be used as a
                                                        -- traveler restriction, as in
                                                        -- "bicycles prohibited on
                                                        -- subways during rush hour" or
                                                        -- "road closed to bicyclists"
   -- Responder Group Affected
   emergency-vehicle-units                    (9729),   -- Default phrase, to be used
                                                        -- when one of the below does not
                                                        -- fit better
   federal-law-enforcement-units              (9730),   
   state-police-units                         (9731),   
   county-police-units                        (9732),   -- Hint: also sheriff response
                                                        -- units
   local-police-units                         (9733),   
   ambulance-units                            (9734),   
   rescue-units                               (9735),   
   fire-units                                 (9736),   
   hAZMAT-units                               (9737),   -- Any vehicle assigned to HAZMAT
                                                        -- duties
   light-tow-unit                             (9738),   
   heavy-tow-unit                             (9739),   
   private-tow-units                          (9743),   -- For 3rd Party tow trucks
   freeway-service-patrols                    (9740),   
   transportation-response-units              (9741),   
   private-contractor-response-units          (9742),   
   -- Incident Response Equipment
   ground-fire-suppression                    (9985),   
   heavy-ground-equipment                     (9986),   
   aircraft                                   (9988),   
   marine-equipment                           (9989),   
   support-equipment                          (9990),   
   medical-rescue-unit                        (9991),   
   other                                      (9993),   -- Depreciated by fire standards,
                                                        -- do not use
   ground-fire-suppression-other              (9994),   
   engine                                     (9995),   
   truck-or-aerial                            (9996),   
   quint                                      (9997),   -- A five-function type of fire
                                                        -- apparatus. The units in the
                                                        -- movie Backdraft were quints
   tanker-pumper-combination                  (9998),   
   brush-truck                                (10000),  
   aircraft-rescue-firefighting               (10001),  
   heavy-ground-equipment-other               (10004),  
   dozer-or-plow                              (10005),  
   tractor                                    (10006),  
   tanker-or-tender                           (10008),  
   aircraft-other                             (10024),  
   aircraft-fixed-wing-tanker                 (10025),  
   helitanker                                 (10026),  
   helicopter                                 (10027),  
   marine-equipment-other                     (10034),  
   fire-boat-with-pump                        (10035),  
   boat-no-pump                               (10036),  
   support-apparatus-other                    (10044),  
   breathing-apparatus-support                (10045),  
   light-and-air-unit                         (10046),  
   medical-rescue-unit-other                  (10054),  
   rescue-unit                                (10055),  
   urban-search-rescue-unit                   (10056),  
   high-angle-rescue                          (10057),  
   crash-fire-rescue                          (10058),  
   bLS-unit                                   (10059),  
   aLS-unit                                   (10060),  
   mobile-command-post                        (10075),  -- Deprecated, do not use
   chief-officer-car                          (10076),  
   hAZMAT-unit                                (10077),  
   type-i-hand-crew                           (10078),  
   type-ii-hand-crew                          (10079),  
   privately-owned-vehicle                    (10083),  -- (Often found in volunteer fire
                                                        -- teams)
   other-apparatus-resource                   (10084),  -- (Remapped from fire code zero)
   ambulance                                  (10085),  
   bomb-squad-van                             (10086),  
   combine-harvester                          (10087),  
   construction-vehicle                       (10088),  
   farm-tractor                               (10089),  
   grass-cutting-machines                     (10090),  
   hAZMAT-containment-tow                     (10091),  
   heavy-tow                                  (10092),  
   light-tow                                  (10094),  
   flatbed-tow                                (10114),  
   hedge-cutting-machines                     (10093),  
   mobile-crane                               (10095),  
   refuse-collection-vehicle                  (10096),  
   resurfacing-vehicle                        (10097),  
   road-sweeper                               (10098),  
   roadside-litter-collection-crews           (10099),  
   survey-crews                               (10115),  
   salvage-vehicle                            (10100),  
   sand-truck                                 (10101),  
   snowplow                                   (10102),  
   steam-roller                               (10103),  
   swat-team-van                              (10104),  
   track-laying-vehicle                       (10105),  
   unknown-vehicle                            (10106),  
   white-lining-vehicle                       (10107),  -- Consider using Roadwork "road
                                                        -- marking operations" unless the
                                                        -- objective is to refer to the
                                                        -- specific vehicle of this type.
                                                        -- Alternative Rendering: line
                                                        -- painting vehicle
   dump-truck                                 (10108),  
   supervisor-vehicle                         (10109),  
   snow-blower                                (10110),  
   rotary-snow-blower                         (10111),  
   road-grader                                (10112),  -- Alternative term: motor grader
   steam-truck                                (10113),  -- A special truck that thaws
                                                        -- culverts and storm drains
   -- Asset Status
   unknown-status                             (10240),  -- Used when status is not known
   ready-for-use                              (10241),  
   working-normally                           (10242),  
   working-autonomously                       (10243),  
   working-incorrectly                        (10244),  
   not-working                                (10245),  
   normal-maintenance                         (10246),  
   in-route-to-use                            (10247),  
   returning-from-use                         (10248),  
   out-of-service                             (10249),  
   off-duty                                   (10250),  
   on-patrol                                  (10251),  
   on-call                                    (10252),  
   on-break                                   (10253),  
   mandatory-time-off                         (10254),  
   low-on-fuel                                (10255),  
   low-on-water                               (10256),  
   low-charge                                 (10257),  
   missing                                    (10258),  -- Use "sign down" in device
                                                        -- status if an object is damaged
                                                        -- (or use "damaged") and could
                                                        -- be returned to service, use
                                                        -- "missing" only if an object is
                                                        -- in fact missing
   -- Roadside Assets
   -- Inanimate Objects
   none                                       (10496),  -- Implies free text follows
   light-pole                                 (10497),  
   utility-pole                              (10498),  
   gantry-way                                 (10499),  
   sign-support                               (10500),  -- All forms of signage
   signal-pole                                (10501),  
   signage-public                             (10502),  
   signage-private                            (10503),  
   overhead-sign                              (10568),  
   ground-sign                                (10569),  
   cones                                      (10504),  -- Typical std height cones as
                                                        -- per MUTCD
   cones-post-type                            (10505),  -- Also called channelizer cones
                                                        -- or delineator posts
   cones-glue-post                            (10506),  -- For all glue-down types
   cones-other                                (10507),  -- Specialty types or misc.
                                                        -- smaller cones
   barriers                                   (10508),  
   barrier-Aframe                             (10509),  -- Sizes larger than 1.5 meters
                                                        -- in length
   barriers-heavy-duty                        (10510),  -- All types requiring equipment
                                                        -- to place
   barricade-type-III                         (10511),  -- All collapsible Type III
                                                        -- Barricades
   barricade-small                            (10512),  -- Type I and all small A frame
                                                        -- types, also so-called "mini"
                                                        -- or "narrows" types
   solid-barrier                              (10565),  
   moveable-barrier                           (10566),  
   barricade-lights                           (10513),  -- Std 7" light as per ITE stds
   beacon                                     (10514),  -- All types of strobe and
                                                        -- rotating lights
   t-stand                                    (10515),  
   a-stand                                    (10516),  
   drums                                      (10517),  -- Common drums and barrel types
   sand-barrel                                (10567),  
   impact-attenuator                          (10518),  -- Water-filled and other
                                                        -- crushable types
   barricade-tape                             (10519),  -- Lettering type (legend) to be
                                                        -- conveyed elsewhere
   safety-fence                               (10520),  
   temp-pavement-markings                     (10521),  -- All forms of temp markings
   speed-bumps                                (10522),  -- Use also for speed humps
   temp-curbs                                 (10523),  
   parking-blocks                             (10524),  
   signboard-fixed                            (10525),  
   signboard-portable                         (10526),  
   stripe                                     (10572),  
   island                                     (10573),  -- Used for raised islands
                                                        -- in median
   -- Controllable or Active Objects
   har                                        (10527),  -- Transmission type not known
   har-AM                                     (10528),  
   har-FM                                     (10529),  
   har-DSRC                                   (10530),  
   traffic-light                              (10531),  -- Also used for signalized
                                                        -- intersections
   lane-control-signal                        (10532),  
   traffic-detector                           (10533),  
   vehicle-detector                           (10534),  
   system-alarm                               (10535),  
   arrow-board                                (10536),  
   fixed-VMS                                  (10537),  
   mobile-VMS                                 (10538),  
   ramp-control                               (10539),  
   gate-control                               (10540),  -- Other than rail types
   temporary-traffic-light                    (10541),  
   over-height-warning-system                 (10542),  
   over-weight-warning-system                 (10543),  
   emergency-telephones                       (10544),  
   railroad-crossing-equipment                (10545),  
   tunnel-ventilation                         (10546),  -- Use also for fans
   ccTV                                       (10547),  
   environmental-sensor                       (10548),  
   emergency-signal                           (10570),  
   countdown-pedestrian-sign                  (10571),  
   -- Items Used by Rail and Transit
   switch                                     (10549),  -- In the context of a railroad
                                                        -- device
   signal                                     (10550),  -- In the context of a railroad
                                                        -- device
   third-rail                                 (10551),  
   overhead-power                             (10552),  -- Specifically the power feed
                                                        -- line for a vehicle, do not use
                                                        -- for general power lines
   concrete-tie                               (10553),  
   wooden-tie                                 (10554),  
   manhole-cover                              (10559),  
   -- Misc. Items
   culvert                                    (10560),  
   escalator                                  (10555),  
   elevator                                   (10556),  
   snow-poles                                 (10561),  -- A tall pole and overhanging
                                                        -- arm (like a luminaire) with
                                                        -- reflective markers to help
                                                        -- indicate roadway in mountain
                                                        -- passes during whiteout
                                                        -- conditions
   track                                      (10557),  
   guide-poles                                (10562),  -- Poles along road to indicate
                                                        -- guard rail in deep snow
   drawbridge                                 (10558),  
   expansion-joint                            (10563),  
   shifted-plate                              (10564),  
   -- Transit Operations
   unknown-transit-problem                    (10753),  
   sleeping-customer                          (10754),  
   assault-on-passenger                       (10755),  
   assault-on-employee                        (10756),  
   broken-seat                                (10757),  
   bus-alarm                                  (10758),  
   crime-or-drug-deal                         (10759),  
   eating-on-board                            (10760),  
   equipment-problem-with-air-conditioning    (10761),  
   equipment-problem-with-air-system          (10762),  
   equipment-problem-with-brakes              (10763),  
   equipment-problem-with-chassis-or-suspension (10764),  
   equipment-problem-with-cooling-system      (10765),  
   equipment-problem-with-doors               (10766),  
   equipment-problem-with-electrical          (10767),  
   equipment-problem-with-engine              (10768),  
   equipment-problem-with-exterior-or-body    (10769),  
   equipment-problem-with-fare-collection     (10770),  
   equipment-problem-with-fuel-or-exhaust     (10771),  
   equipment-problem-with-horn                (10772),  
   equipment-problem-with-interior            (10773),  
   equipment-problem-with-liftkneeling        (10774),  
   equipment-problem-with-lights              (10775),  
   equipment-problem-with-lubrication         (10776),  
   equipment-problem-with-radio-or-communication (10777),  
   equipment-problem-with-signs               (10778),  
   equipment-problem-with-steering            (10779),  
   equipment-problem-with-tires               (10780),  
   equipment-problem-with-transmission        (10781),  
   equipment-problem-with-unknown-alarm       (10782),  
   equipment-problem-with-wipers              (10783),  
   fare-dispute-expired-pass                  (10784),  
   fare-dispute-expired-transfer              (10785),  
   fare-dispute-expired-upgrade               (10786),  
   fare-dispute-other                         (10787),  
   fare-dispute-refuses-to-pay                (10788),  
   lift-passenger-cycle-completed             (10789),  
   lift-passenger-ready-to-alight             (10790),  
   lift-passenger-ready-to-board              (10791),  
   lost-article                               (10792),  
   objects-thrown                             (10793),  
   passenger-accident-alighting               (10794),  
   passenger-accident-boarding                (10795),  
   passenger-accident-fallen-on-board         (10796),  
   passenger-load                             (10797),  
   passenger-accident-other                   (10798),  
   passenger-sick-or-injured                  (10799),  
   right-of-way                               (10800),  
   theft                                      (10801),  
   theft-of-service                           (10802),  
   waiting-to-get-relief-for-schedule-break   (10803),  
   waiting-to-get-relief-after-run-is-finished (10804),  
   waiting-to-provide-relief                  (10805),  
   -- Objects
   -- Misc Items
   unknown-object                             (11009),  
   tire                                       (11010),  
   rim                                        (11011),  
   retread                                    (11012),  
   trash                                      (11013),  -- Consider using the
                                                        -- CleanUpItems of IEEE 1512 for
                                                        -- operational needs
   cargo                                      (11014),  
   diesel                                     (11015),  
   gasoline                                   (11016),  -- RM-060
   anti-freeze                                (11017),  
   propane-gas                                (11061),  
   alternative-fuel                           (11060),  -- (Implies CNG)
   seat-belts                                 (11018),  
   litter-container                           (11019),  -- RG-130  Alt term: Trash
                                                        -- Container
   all-Terrain-vehicle                        (11020),  -- Rl-170
   seaplane                                   (11021),  -- RG-260
   chairlift                                  (11022),  -- RS-100
   fishing-pier                               (11023),  -- RW-160
   telephone                                  (11025),  -- RM-150 See also
                                                        -- Emergency-Telephones 10544
   railroad-cross-buck                        (11024),  -- (Used for Railroad
                                                        -- crossings)
   horn                                       (11048),  
   train                                      (11047),  -- The train itself
                                                        -- regardless of the type (not
                                                        -- the mode of transit)
   deer                                       (11049),  -- W11-3
   horse                                      (11051),  -- Use for equestrian as
                                                        -- well
   cattle                                     (11050),  -- W11-4
   golf-cart                                  (11052),  -- W11-10
   services                                   (11056),  
   motorist-services                          (11059),  -- Alt text motor services
                                                        -- D9-18
   food-services                              (11053),  
   roadside-table                             (11055),  
   ambulance-staging-point                    (11054),  -- Use for ambulance station
                                                        -- as well
   -- Shelters-Structures
   fallout                                    (11026),  -- a type of shelter or
                                                        -- structure
   medical                                    (11027),  -- a type of shelter or
                                                        -- structure
   chemical                                   (11028),  -- a type of shelter or
                                                        -- structure
   welfare                                    (11029),  -- a type of shelter or
                                                        -- structure
   decontamination                            (11063),  
   evacuation                                 (11030),  -- a type of shelter or
                                                        -- structure
   registration                               (11062),  -- a type of shelter or
                                                        -- structure
   emergency                                  (11064),  --Use only when no other
                                                        -- type is known
   -- Signal States
   left-arrow-signal                          (11031),  
   ahead-arrow-signal                         (11032),  
   right-arrow-signal                         (11033),  
   green-light-signal                         (11034),  
   green-arrow-signal                         (11035),  
   yellow-light-signal                        (11036),  
   yellow-arrow-signal                        (11037),  
   red-light-signal                           (11038),  
   red-arrow-signal                           (11039),  
   extended-green-signal                      (11040),  
   advance-arrow-signal                       (11041),  
   pedestrian-Signal-Stop                     (11042),  -- Used for donÃ¢â‚¬â„¢t walk sign
   pedestrian-Signal-Caution                  (11043),  -- Used for donÃ¢â‚¬â„¢t start to
                                                        -- walk
   pedestrian-Signal-Walk                     (11044),  
   pedestrian-Signal-Light                    (11045),  -- Use for light itself
                                                        -- (regardless of state)
   pedestrian-Signal-Time-Display             (11046),  -- Use for count down timer
                                                        -- display
   -- Valid Maneuvers
   prohibit-None-Allowed-LU-LT-L45-S-R45-RT-RU (11264),  
   prohibit-RU-Allowed-LU-LT-L45-S-R45-RT     (11265),  -- All Maneuvers allowed
   prohibit-RT-Allowed-LU-LT-L45-S-R45-RU     (11266),  
   prohibit-RT-RU-Allowed-LU-LT-L45-S-R45     (11267),  
   prohibit-R45-Allowed-LU-LT-L45-S-RT-RU     (11268),  
   prohibit-R45-RU-Allowed-LU-LT-L45-S-RT     (11269),  
   prohibit-R45-RT-Allowed-LU-LT-L45-S-RU     (11270),  
   prohibit-R45-RT-RU-Allowed-LU-LT-L45-S     (11271),  -- Left or Straight Only
                                                        -- (R3-6), Right Turn prohibited
   prohibit-S-Allowed-LU-LT-L45-R45-RT-RU     (11272),  
   prohibit-S-RU-Allowed-LU-LT-L45-R45-RT     (11273),  
   prohibit-S-RT-Allowed-LU-LT-L45-R45-RU     (11274),  
   prohibit-S-RT-RU-Allowed-LU-LT-L45-R45     (11275),  
   prohibit-S-R45-Allowed-LU-LT-L45-RT-RU     (11276),  
   prohibit-S-R45-RU-Allowed-LU-LT-L45-RT     (11277),  
   prohibit-S-R45-RT-Allowed-LU-LT-L45-RU     (11278),  
   prohibit-S-R45-RT-RU-Allowed-LU-LT-L45     (11279),  
   prohibit-L45-Allowed-LU-LT-S-R45-RT-RU     (11280),  -- Left 45 deg turn
                                                        -- prohibited
   prohibit-L45-RU-Allowed-LU-LT-S-R45-RT     (11281),  
   prohibit-L45-RT-Allowed-LU-LT-S-R45-RU     (11282),  
   prohibit-L45-RT-RU-Allowed-LU-LT-S-R45     (11283),  
   prohibit-L45-R45-Allowed-LU-LT-S-RT-RU     (11284),  
   prohibit-L45-R45-RU-Allowed-LU-LT-S-RT     (11285),  
   prohibit-L45-R45-RT-Allowed-LU-LT-S-RU     (11286),  
   prohibit-L45-R45-RT-RU-Allowed-LU-LT-S     (11287),  
   prohibit-L45-S-Allowed-LU-LT-R45-RT-RU     (11288),  
   prohibit-L45-S-RU-Allowed-LU-LT-R45-RT     (11289),  
   prohibit-L45-S-RT-Allowed-LU-LT-R45-RU     (11290),  
   prohibit-L45-S-RT-RU-Allowed-LU-LT-R45     (11291),  
   prohibit-L45-S-R45-Allowed-LU-LT-RT-RU     (11292),  
   prohibit-L45-S-R45-RU-Allowed-LU-LT-RT     (11293),  
   prohibit-L45-S-R45-RT-Allowed-LU-LT-RU     (11294),  
   prohibit-L45-S-R45-RT-RU-Allowed-LU-LT     (11295),  -- Left U-Turn and Left Turn
                                                        -- Allowed
   prohibit-LT-Allowed-LU-L45-S-R45-RT-RU     (11296),  -- Left Turn Prohibited
                                                        -- (R3-2)
   prohibit-LT-RU-Allowed-LU-L45-S-R45-RT     (11297),  
   prohibit-LT-RT-Allowed-LU-L45-S-R45-RU     (11298),  -- Left and Right Turn
                                                        -- Prohibited  (R3-3), Straight
                                                        -- Only
   prohibit-LT-RT-RU-Allowed-LU-L45-S-R45     (11299),  
   prohibit-LT-R45-Allowed-LU-L45-S-RT-RU     (11300),  
   prohibit-LT-R45-RU-Allowed-LU-L45-S-RT     (11301),  
   prohibit-LT-R45-RT-Allowed-LU-L45-S-RU     (11302),  
   prohibit-LT-R45-RT-RU-Allowed-LU-L45-S     (11303),  
   prohibit-LT-S-Allowed-LU-L45-R45-RT-RU     (11304),  -- Straight Ahead Prohibited
   prohibit-LT-S-RU-Allowed-LU-L45-R45-RT     (11305),  
   prohibit-LT-S-RT-Allowed-LU-L45-R45-RU     (11306),  
   prohibit-LT-S-RT-RU-Allowed-LU-L45-R45     (11307),  
   prohibit-LT-S-R45-Allowed-LU-L45-RT-RU     (11308),  
   prohibit-LT-S-R45-RU-Allowed-LU-L45-RT     (11309),  
   prohibit-LT-S-R45-RT-Allowed-LU-L45-RU     (11310),  
   prohibit-LT-S-R45-RT-RU-Allowed-LU-L45     (11311),  
   prohibit-LT-L45-Allowed-LU-S-R45-RT-RU     (11312),  
   prohibit-LT-L45-RU-Allowed-LU-S-R45-RT     (11313),  
   prohibit-LT-L45-RT-Allowed-LU-S-R45-RU     (11314),  
   prohibit-LT-L45-RT-RU-Allowed-LU-S-R45     (11315),  
   prohibit-LT-L45-R45-Allowed-LU-S-RT-RU     (11316),  
   prohibit-LT-L45-R45-RU-Allowed-LU-S-RT     (11317),  
   prohibit-LT-L45-R45-RT-Allowed-LU-S-RU     (11318),  
   prohibit-LT-L45-R45-RT-RU-Allowed-LU-S     (11319),  
   prohibit-LT-L45-S-Allowed-LU-R45-RT-RU     (11320),  
   prohibit-LT-L45-S-RU-Allowed-LU-R45-RT     (11321),  
   prohibit-LT-L45-S-RT-Allowed-LU-R45-RU     (11322),  
   prohibit-LT-L45-S-RT-RU-Allowed-LU-R45     (11323),  
   prohibit-LT-L45-S-R45-Allowed-LU-RT-RU     (11324),  
   prohibit-LT-L45-S-R45-RU-Allowed-LU-RT     (11325),  
   prohibit-LT-L45-S-R45-RT-Allowed-LU-RU     (11326),  
   prohibit-LT-L45-S-R45-RT-RU-Allowed-LU     (11327),  -- Left U-Turn Allowed
   prohibit-LU-Allowed-LT-L45-S-R45-RT-RU     (11328),  -- Left U-Turn Prohibited
                                                        -- (R3-4)
   prohibit-LU-RU-Allowed-LT-L45-S-R45-RT     (11329),  
   prohibit-LU-RT-Allowed-LT-L45-S-R45-RU     (11330),  
   prohibit-LU-RT-RU-Allowed-LT-L45-S-R45     (11331),  
   prohibit-LU-R45-Allowed-LT-L45-S-RT-RU     (11332),  
   prohibit-LU-R45-RU-Allowed-LT-L45-S-RT     (11333),  
   prohibit-LU-R45-RT-Allowed-LT-L45-S-RU     (11334),  
   prohibit-LU-R45-RT-RU-Allowed-LT-L45-S     (11335),  
   prohibit-LU-S-Allowed-LT-L45-R45-RT-RU     (11336),  
   prohibit-LU-S-RU-Allowed-LT-L45-R45-RT     (11337),  
   prohibit-LU-S-RT-Allowed-LT-L45-R45-RU     (11338),  
   prohibit-LU-S-RT-RU-Allowed-LT-L45-R45     (11339),  
   prohibit-LU-S-R45-Allowed-LT-L45-RT-RU     (11340),  
   prohibit-LU-S-R45-RU-Allowed-LT-L45-RT     (11341),  
   prohibit-LU-S-R45-RT-Allowed-LT-L45-RU     (11342),  
   prohibit-LU-S-R45-RT-RU-Allowed-LT-L45     (11343),  
   prohibit-LU-L45-Allowed-LT-S-R45-RT-RU     (11344),  
   prohibit-LU-L45-RU-Allowed-LT-S-R45-RT     (11345),  
   prohibit-LU-L45-RT-Allowed-LT-S-R45-RU     (11346),  
   prohibit-LU-L45-RT-RU-Allowed-LT-S-R45     (11347),  
   prohibit-LU-L45-R45-Allowed-LT-S-RT-RU     (11348),  
   prohibit-LU-L45-R45-RU-Allowed-LT-S-RT     (11349),  
   prohibit-LU-L45-R45-RT-Allowed-LT-S-RU     (11350),  
   prohibit-LU-L45-R45-RT-RU-Allowed-LT-S     (11351),  -- Left Turn and Straight
                                                        -- Ahead Only
   prohibit-LU-L45-S-Allowed-LT-R45-RT-RU     (11352),  
   prohibit-LU-L45-S-RU-Allowed-LT-R45-RT     (11353),  
   prohibit-LU-L45-S-RT-Allowed-LT-R45-RU     (11354),  
   prohibit-LU-L45-S-RT-RU-Allowed-LT-R45     (11355),  
   prohibit-LU-L45-S-R45-Allowed-LT-RT-RU     (11356),  
   prohibit-LU-L45-S-R45-RU-Allowed-LT-RT     (11357),  -- Left Turn and Right Turn
                                                        -- Only
   prohibit-LU-L45-S-R45-RT-Allowed-LT-RU     (11358),  
   prohibit-LU-L45-S-R45-RT-RU-Allowed-LT     (11359),  -- Left Turn Only  (R3-5)
   prohibit-LU-LT-Allowed-L45-S-R45-RT-RU     (11360),  -- Left U-Turn and Left Turn
                                                        -- Prohibited  (R3-18)
   prohibit-LU-LT-RU-Allowed-L45-S-R45-RT     (11361),  
   prohibit-LU-LT-RT-Allowed-L45-S-R45-RU     (11362),  
   prohibit-LU-LT-RT-RU-Allowed-L45-S-R45     (11363),  
   prohibit-LU-LT-R45-Allowed-L45-S-RT-RU     (11364),  
   prohibit-LU-LT-R45-RU-Allowed-L45-S-RT     (11365),  
   prohibit-LU-LT-R45-RT-Allowed-L45-S-RU     (11366),  
   prohibit-LU-LT-R45-RT-RU-Allowed-L45-S     (11367),  
   prohibit-LU-LT-S-Allowed-L45-R45-RT-RU     (11368),  
   prohibit-LU-LT-S-RU-Allowed-L45-R45-RT     (11369),  
   prohibit-LU-LT-S-RT-Allowed-L45-R45-RU     (11370),  
   prohibit-LU-LT-S-RT-RU-Allowed-L45-R45     (11371),  
   prohibit-LU-LT-S-R45-Allowed-L45-RT-RU     (11372),  
   prohibit-LU-LT-S-R45-RU-Allowed-L45-RT     (11373),  
   prohibit-LU-LT-S-R45-RT-Allowed-L45-RU     (11374),  
   prohibit-LU-LT-S-R45-RT-RU-Allowed-L45     (11375),  
   prohibit-LU-LT-L45-Allowed-S-R45-RT-RU     (11376),  -- Right Turn or Straight
                                                        -- Only  
   prohibit-LU-LT-L45-RU-Allowed-S-R45-RT     (11377),  
   prohibit-LU-LT-L45-RT-Allowed-S-R45-RU     (11378),  
   prohibit-LU-LT-L45-RT-RU-Allowed-S-R45     (11379),  
   prohibit-LU-LT-L45-R45-Allowed-S-RT-RU     (11380),  
   prohibit-LU-LT-L45-R45-RU-Allowed-S-RT     (11381),  
   prohibit-LU-LT-L45-R45-RT-Allowed-S-RU     (11382),  
   prohibit-LU-LT-L45-R45-RT-RU-Allowed-S     (11383),  -- Straight Ahead Only
                                                        -- (R3-5a)
   prohibit-LU-LT-L45-S-Allowed-R45-RT-RU     (11384),  
   prohibit-LU-LT-L45-S-RU-Allowed-R45-RT     (11385),  
   prohibit-LU-LT-L45-S-RT-Allowed-R45-RU     (11386),  
   prohibit-LU-LT-L45-S-RT-RU-Allowed-R45     (11387),  
   prohibit-LU-LT-L45-S-R45-Allowed-RT-RU     (11388),  
   prohibit-LU-LT-L45-S-R45-RU-Allowed-RT     (11389),  -- Right Turn Only 
   prohibit-LU-LT-L45-S-R45-RT-Allowed-RU     (11390),  
   prohibit-LU-LT-L45-S-R45-RT-RU-Allowed-None (11391),  -- All Maneuvers are
                                                        -- Prohibited
   -- Large Numbers
   n1-16th                                    (11521),  -- The fraction 1/16th
   n1-10th                                    (11522),  -- The fraction 1/10th
   n1-8th                                     (11523),  -- The fraction 1/8th
   n1-4th                                     (11524),  -- The fraction 1/4th
   n1-3rd                                     (11525),  -- The fraction 1/3rd
   n1-2                                       (11526),  -- The fraction 1/2
   n3-4                                       (11527),  -- The fraction 3/4th
   n300                                       (11531),  
   n350                                       (11532),  
   n400                                       (11533),  
   n450                                       (11534),  
   n500                                       (11535),  
   n550                                       (11536),  
   n600                                       (11537),  
   n650                                       (11538),  
   n700                                       (11539),  
   n750                                       (11540),  
   n800                                       (11541),  
   n850                                       (11542),  
   n900                                       (11543),  
   n950                                       (11544),  
   n1000                                      (11545),  
   n1100                                      (11546),  
   n1200                                      (11547),  
   n1300                                      (11548),  
   n1400                                      (11549),  
   n1500                                      (11550),  
   n1600                                      (11551),  
   n1700                                      (11552),  
   n1800                                      (11553),  
   n1900                                      (11554),  
   n2000                                      (11555),  
   n2100                                      (11556),  
   n2200                                      (11557),  
   n2300                                      (11558),  
   n2400                                      (11559),  
   n2500                                      (11560),  
   n2600                                      (11561),  
   n2700                                      (11562),  
   n2800                                      (11563),  
   n2900                                      (11564),  
   n3000                                      (11565),  
   n3500                                      (11566),  
   n4000                                      (11567),  
   n4500                                      (11568),  
   n5000                                      (11569),  
   n5500                                      (11570),  
   n6000                                      (11571),  
   n6500                                      (11572),  
   n7000                                      (11573),  
   n7500                                      (11574),  
   n8000                                      (11575),  
   n8500                                      (11576),  
   n9000                                      (11577),  
   n9500                                      (11578),  
   n10000                                     (11579),  
   n11000                                     (11580),  
   n12000                                     (11581),  
   n13000                                     (11582),  
   n14000                                     (11583),  
   n15000                                     (11584),  
   n16000                                     (11585),  
   n17000                                     (11586),  
   n18000                                     (11587),  
   n19000                                     (11588),  
   n20000                                     (11589),  
   n21000                                     (11590),  
   n22000                                     (11591),  
   n23000                                     (11592),  
   n24000                                     (11593),  
   n25000                                     (11594),  
   n26000                                     (11595),  
   n27000                                     (11596),  
   n28000                                     (11597),  
   n29000                                     (11598),  
   n30000                                     (11599),  
   n35000                                     (11600),  
   n40000                                     (11601),  
   n45000                                     (11602),  
   n50000                                     (11603),  
   n55000                                     (11604),  
   n60000                                     (11605),  
   n65000                                     (11606),  
   n70000                                     (11607),  
   n75000                                     (11608),  
   n80000                                     (11609),  
   n85000                                     (11610),  
   n90000                                     (11611),  
   n95000                                     (11612),  
   n100000                                    (11613),  
   -- Named Objects
   name-follows                               (11777),  -- Used for other types of
                                                        -- named objects to delimit name
   freeway                                    (11778),  -- Typically followed by
                                                        -- name
   us-Route                                   (11779),  -- Typically followed by
                                                        -- name, M1-4
   state-Route                                (11780),  -- Typically followed by
                                                        -- name, M1-5
   interstate                                 (11781),  -- Typically followed by
                                                        -- name, M1-1
   business-Loop                              (11782),  -- Typically followed by
                                                        -- name, M1-2, M4-3
   spur                                       (11797),  -- Typically followed by
                                                        -- name, M1-3
   junction                                    (11798),  -- Typically followed by
                                                        -- names, M2-1, M2-2
   alternative                                (11783),  -- Typically followed by
                                                        -- name, M4-1, M4-1a
   county-Route                               (11784),  -- Typically followed by
                                                        -- name, M1-6
   forest-Route                               (11785),  -- Typically followed by
                                                        -- name, M1-7
   farm-to-Market-Route                       (11786),  -- Typically followed by
                                                        -- name
   eisenhower-Interstate-System               (11787),  -- Typically followed by
                                                        -- name, M1-10
   americas-Byways                            (11788),  -- Typically followed by
                                                        -- name, Alt term: National
                                                        -- Scenic Byways
   national-Network-Route                     (11789),  -- Typically followed by
                                                        -- name
   scenic-Area                                (11790),  -- Typically followed by
                                                        -- name
   parking-Area                               (11791),  -- Typically followed by
                                                        -- name
   weight-Station                             (11792),  -- Typically followed by
                                                        -- name
   road                                       (11793),  -- Typically followed by
                                                        -- name (all types of roads and
                                                        -- streets not otherwise listed
                                                        -- above)
   exit                                       (11794),  -- Typically followed by
                                                        -- name
   historical-route                           (11795),  -- Typically followed by
                                                        -- name
   state-line                                 (11796),  -- Preceded by a state name
                                                        -- I-2
   bicycle-route                               (11799),  -- Typically followed by
                                                        -- name, M1-8
   bicycle-interstate-route                    (11800),  -- Typically followed by
                                                        -- name, M1-9
   national-park                              (11801),  -- Typically preceded by
                                                        -- name, D7-1, D7-2
   -- Recreational Objects and Activities
   -- General Items
   bear-viewing-area                          (12033),  -- RG-020
   deer-viewing-area                          (12034),  -- RG-040
   drinking-water                             (12035),  -- RG-050
   environmental-study-area                   (12036),  -- RG-060
   falling-rocks                              (12037),  -- RG-070 See also ITIS
                                                        -- code: Rockfall 1309
   firearms                                   (12038),  -- RG-080
   leashed-pets                               (12039),  -- RG-110
   point-of-interest                          (12040),  -- RG-160
   smoking                                    (12041),  -- RG-180
   dog                                        (12042),  -- RG-240
   tent-camping                               (12043),  -- RM-010
   trailer-camping                            (12044),  -- RM-020
   first-aid                                  (12045),  -- RM-040
   handicapped                                (12046),  -- RM-080
   mechanic                                   (12047),  -- RM-100
   trailer-sanitary-station                   (12048),  -- RM-160  Alt: Trailer
                                                        -- Waste Station
   viewing-area                               (12049),  -- RM-170
   scenic-overlook                            (12095),  -- For D6-2
   campfire                                   (12050),  -- RA-030
   locker                                     (12051),  -- RA-070
   sleeping                                   (12052),  -- RA-110 As in Sleeping
                                                        -- Shelter
   trail                                      (12053),  -- RA-120 As in Trail
                                                        -- Shelter
   climbing                                   (12054),  -- RL-020
   rock-climbing                              (12055),  -- RL-030
   hunting                                    (12056),  -- RL-040
   playground                                 (12057),  -- RL-050
   rock-collecting                            (12058),  -- RL-060
   spelunking                                 (12059),  -- RL-070
   bicycle-trail                              (12060),  -- RL-090
   hiking-trail                               (12061),  -- RL-100
   horse-trail                                (12062),  -- RL-110
   trail-interpretive-auto                    (12063),  -- RL-120
   trail-interpretive-pedestrian              (12064),  -- RL-130
   trail-road-for-4WD-vehicles                (12065),  -- RL-140
   trail-for-trail-bikes                      (12066),  -- RL-150
   archer                                     (12067),  -- RL-190
   hang-glider                                (12068),  -- RL-210
   -- Water Related
   boat-tours                                 (12069),  -- RW-010
   canoeing                                   (12070),  -- RW-020
   diving                                     (12071),  -- RW-030
   scuba-diving                               (12072),  -- RW-040
   fishing                                    (12073),  -- RW-050
   marine-recreation-area                     (12074),  -- RW-060
   motorboating                               (12075),  -- RW-070
   boat-ramp                                  (12076),  -- RW-080
   rowboating                                 (12077),  -- RW-090
   sailboating                                (12078),  -- RW-100
   water-skiing                               (12079),  -- RW-110
   surfing                                    (12080),  -- RW-120
   swimming                                   (12081),  -- RW-130
   wading                                     (12082),  -- RW-140
   hand-launch                                (12083),  -- RW-170
   kayak                                      (12084),  -- RW-190
   wind-surf                                  (12085),  -- RW-210
   -- Winter-Snow Related
   ice-skating                                (12086),  -- RS-010
   ski-jumping                                (12087),  -- RS-020
   bobbing                                    (12088),  -- RS-030
   cross-country-skiing                       (12089),  -- RS-040
   downhill-skiing                            (12090),  -- RS-050
   sledding                                   (12091),  -- RS-060
   snowmobiling                               (12092),  -- RS-070
   snowshoeing                                (12093),  -- RS-080
   winter-recreation-area                     (12094),  -- RS-090
   -- Regulatory and Warning Signs
   -- MUTCD Signage Types
   regulatory-sign                            (12289),  -- Followed by sign data
   warning-sign                               (12290),  -- Followed by sign data
   information-sign                           (12291),  -- Followed by sign data
   construction-sign                          (12292),  -- Followed by sign data
   guide-sign                                 (12293),  -- Followed by sign data
   -- MUCTD Basic Signs
   stop                                       (12294),  
   yield                                      (12295),  
   caution                                    (12330),  
   temporary                                  (12331),  
   to-oncoming-traffic                        (12296),  
   four-way                                   (12297),  -- As in 4-way stop
   all-way                                    (12298),  -- All directions of travel
                                                        -- allowed or all lanes at a
                                                        -- junction
   one-way                                    (12329),  -- One direction of travel
                                                        -- allowed
   -- MUCTD Sign Fragments
   zone                                       (12299),  -- Typically preceded by
                                                        -- type of zone
   narrows                                    (12300),  -- Used as an MUTCD sign,
                                                        -- typically preceded by road
   widens                                     (12301),  -- Used as an MUTCD sign,
                                                        -- typically preceded by road
   reduced                                    (12302),  -- Used as an MUTCD sign,
                                                        -- typically preceded by road or
                                                        -- lane
   combined                                   (12303),  
   minimum                                    (12304),  
   maximum                                    (12305),  
   divided-road                               (12306),  -- Use for divided highway
                                                        -- as well
   double-arrow                               (12307),  
   dead-end                                   (12308),  
   no-outlet                                  (12309),  
   wrong-way                                  (12310),  -- R-5-1a
   do-not-enter                               (12314),  -- R-5-1
   nDetour                                     (12312),  -- Typically followed by
                                                        -- arrows and distance
   chevron                                    (12313),  
   -- MUCTD Intersection Graphics
   t-intersection-to-the-side                 (12315),  
   t-intersection-oncoming                    (12316),  -- Use for W2-4 graphic
   y-intersection-to-the-side                 (12317),  
   y-intersection-oncoming                    (12318),  -- Use for W2-5 graphic
   four-way-divided-highway-crossing          (12319),  -- Use for R6-3 graphic
   t-way-divided-highway-crossing             (12320),  -- Use for R6-3a graphic
   light-rail-divided-highway-crossing        (12321),  -- Use for R15-7 graphic
   light-rail-t-divided-highway-crossing      (12322),  -- Use for R15-7a graphic
   side-road-to-right                         (12323),  -- Use for W2-2R graphic
   side-road-to-left                          (12324),  -- Use for W2-2L graphic
   side-road-to-right-at-angle                (12325),  -- Use for W2-3R graphic
   side-road-to-left-at-angle                 (12326),  -- Use for W2-3L graphic
   entering-roadway-merge                     (12327),  -- Use for W4-5 graphic
   entering-roadway-added-lane                (12328),  -- Use for W4-6 graphic
   -- Small Numbers
   n1                                         (12545),  
   n2                                         (12546),  
   n3                                         (12547),  
   n4                                         (12548),  
   n5                                         (12549),  
   n6                                         (12550),  
   n7                                         (12551),  
   n8                                         (12552),  
   n9                                         (12553),  
   n10                                        (12554),  
   n11                                        (12555),  
   n12                                        (12556),  
   n13                                        (12557),  
   n14                                        (12558),  
   n15                                        (12559),  
   n16                                        (12560),  
   n17                                        (12561),  
   n18                                        (12562),  
   n19                                        (12563),  
   n20                                        (12564),  
   n21                                        (12565),  
   n22                                        (12566),  
   n23                                        (12567),  
   n24                                        (12568),  
   n25                                        (12569),  
   n26                                        (12570),  
   n27                                        (12571),  
   n28                                        (12572),  
   n29                                        (12573),  
   n30                                        (12574),  
   n31                                        (12575),  
   n32                                        (12576),  
   n33                                        (12577),  
   n34                                        (12578),  
   n35                                        (12579),  
   n36                                        (12580),  
   n37                                        (12581),  
   n38                                        (12582),  
   n39                                        (12583),  
   n40                                        (12584),  
   n41                                        (12585),  
   n42                                        (12586),  
   n43                                        (12587),  
   n44                                        (12588),  
   n45                                        (12589),  
   n46                                        (12590),  
   n47                                        (12591),  
   n48                                        (12592),  
   n49                                        (12593),  
   n50                                        (12594),  
   n51                                        (12595),  
   n52                                        (12596),  
   n53                                        (12597),  
   n54                                        (12598),  
   n55                                        (12599),  
   n56                                        (12600),  
   n57                                        (12601),  
   n58                                        (12602),  
   n59                                        (12603),  
   n60                                        (12604),  
   n61                                        (12605),  
   n62                                        (12606),  
   n63                                        (12607),  
   n64                                        (12608),  
   n65                                        (12609),  
   n66                                        (12610),  
   n67                                        (12611),  
   n68                                        (12612),  
   n69                                        (12613),  
   n70                                        (12614),  
   n71                                        (12615),  
   n72                                        (12616),  
   n73                                        (12617),  
   n74                                        (12618),  
   n75                                        (12619),  
   n76                                        (12620),  
   n77                                        (12621),  
   n78                                        (12622),  
   n79                                        (12623),  
   n80                                        (12624),  
   n81                                        (12625),  
   n82                                        (12626),  
   n83                                        (12627),  
   n84                                        (12628),  
   n85                                        (12629),  
   n86                                        (12630),  
   n87                                        (12631),  
   n88                                        (12632),  
   n89                                        (12633),  
   n90                                        (12634),  
   n91                                        (12635),  
   n92                                        (12636),  
   n93                                        (12637),  
   n94                                        (12638),  
   n95                                        (12639),  
   n96                                        (12640),  
   n97                                        (12641),  
   n98                                        (12642),  
   n99                                        (12643),  
   n100                                       (12644),  
   n101                                       (12645),  
   n102                                       (12646),  
   n103                                       (12647),  
   n104                                       (12648),  
   n105                                       (12649),  
   n106                                       (12650),  
   n107                                       (12651),  
   n108                                       (12652),  
   n109                                       (12653),  
   n110                                       (12654),  
   n111                                       (12655),  
   n112                                       (12656),  
   n113                                       (12657),  
   n114                                       (12658),  
   n115                                       (12659),  
   n116                                       (12660),  
   n117                                       (12661),  
   n118                                       (12662),  
   n119                                       (12663),  
   n120                                       (12664),  
   n121                                       (12665),  
   n122                                       (12666),  
   n123                                       (12667),  
   n124                                       (12668),  
   n125                                       (12669),  
   n126                                       (12670),  
   n127                                       (12671),  
   n128                                       (12672),  
   n129                                       (12673),  
   n130                                       (12674),  
   n131                                       (12675),  
   n132                                       (12676),  
   n133                                       (12677),  
   n134                                       (12678),  
   n135                                       (12679),  
   n136                                       (12680),  
   n137                                       (12681),  
   n138                                       (12682),  
   n139                                       (12683),  
   n140                                       (12684),  
   n141                                       (12685),  
   n142                                       (12686),  
   n143                                       (12687),  
   n144                                       (12688),  
   n145                                       (12689),  
   n146                                       (12690),  
   n147                                       (12691),  
   n148                                       (12692),  
   n149                                       (12693),  
   n150                                       (12694),  
   n151                                       (12695),  
   n152                                       (12696),  
   n153                                       (12697),  
   n154                                       (12698),  
   n155                                       (12699),  
   n156                                       (12700),  
   n157                                       (12701),  
   n158                                       (12702),  
   n159                                       (12703),  
   n160                                       (12704),  
   n161                                       (12705),  
   n162                                       (12706),  
   n163                                       (12707),  
   n164                                       (12708),  
   n165                                       (12709),  
   n166                                       (12710),  
   n167                                       (12711),  
   n168                                       (12712),  
   n169                                       (12713),  
   n170                                       (12714),  
   n171                                       (12715),  
   n172                                       (12716),  
   n173                                       (12717),  
   n174                                       (12718),  
   n175                                       (12719),  
   n176                                       (12720),  
   n177                                       (12721),  
   n178                                       (12722),  
   n179                                       (12723),  
   n180                                       (12724),  
   n181                                       (12725),  
   n182                                       (12726),  
   n183                                       (12727),  
   n184                                       (12728),  
   n185                                       (12729),  
   n186                                       (12730),  
   n187                                       (12731),  
   n188                                       (12732),  
   n189                                       (12733),  
   n190                                       (12734),  
   n191                                       (12735),  
   n192                                       (12736),  
   n193                                       (12737),  
   n194                                       (12738),  
   n195                                       (12739),  
   n196                                       (12740),  
   n197                                       (12741),  
   n198                                       (12742),  
   n199                                       (12743),  
   n200                                       (12744),  
   n201                                       (12745),  
   n202                                       (12746),  
   n203                                       (12747),  
   n204                                       (12748),  
   n205                                       (12749),  
   n206                                       (12750),  
   n207                                       (12751),  
   n208                                       (12752),  
   n209                                       (12753),  
   n210                                       (12754),  
   n211                                       (12755),  
   n212                                       (12756),  
   n213                                       (12757),  
   n214                                       (12758),  
   n215                                       (12759),  
   n216                                       (12760),  
   n217                                       (12761),  
   n218                                       (12762),  
   n219                                       (12763),  
   n220                                       (12764),  
   n221                                       (12765),  
   n222                                       (12766),  
   n223                                       (12767),  
   n224                                       (12768),  
   n225                                       (12769),  
   n226                                       (12770),  
   n227                                       (12771),  
   n228                                       (12772),  
   n229                                       (12773),  
   n230                                       (12774),  
   n231                                       (12775),  
   n232                                       (12776),  
   n233                                       (12777),  
   n234                                       (12778),  
   n235                                       (12779),  
   n236                                       (12780),  
   n237                                       (12781),  
   n238                                       (12782),  
   n239                                       (12783),  
   n240                                       (12784),  
   n241                                       (12785),  
   n242                                       (12786),  
   n243                                       (12787),  
   n244                                       (12788),  
   n245                                       (12789),  
   n246                                       (12790),  
   n247                                       (12791),  
   n248                                       (12792),  
   n249                                       (12793),  
   n250                                       (12794),  
   n251                                       (12795),  
   n252                                       (12796),  
   n253                                       (12797),  
   n254                                       (12798),  
   n255                                       (12799),  
   -- States and Territories
   alabama                                    (12801),  
   alaska                                     (12802),  
   american-Samoa                             (12803),  
   arizona                                    (12804),  
   arkansas                                   (12805),  
   california                                 (12806),  
   colorado                                   (12807),  
   connecticut                                (12808),  
   delaware                                   (12809),  
   district-of-Columbia                       (12810),  
   florida                                    (12811),  
   georgia                                    (12812),  
   guam                                       (12813),  
   hawaii                                     (12814),  
   idaho                                      (12815),  
   illinois                                   (12816),  
   indiana                                    (12817),  
   iowa                                       (12818),  
   kansas                                     (12819),  
   kentucky                                   (12820),  
   louisiana                                  (12821),  
   maine                                      (12822),  
   maryland                                   (12823),  
   massachusetts                              (12824),  
   michigan                                   (12825),  
   minnesota                                  (12826),  
   mississippi                                (12827),  
   missouri                                   (12828),  
   montana                                    (12829),  
   nebraska                                   (12830),  
   nevada                                     (12831),  
   new-Hampshire                              (12832),  
   new-Jersey                                 (12833),  
   new-Mexico                                 (12834),  
   new-York                                   (12835),  
   north-Carolina                             (12836),  
   north-Dakota                               (12837),  
   northern-Marianas-Islands                  (12838),  
   ohio                                       (12839),  
   oklahoma                                   (12840),  
   oregon                                     (12841),  
   pennsylvania                               (12842),  
   puerto-rico                                (12843),  
   rhode-Island                               (12844),  
   south-Carolina                             (12845),  
   south-Dakota                               (12846),  
   tennessee                                  (12847),  
   texas                                      (12848),  
   utah                                       (12849),  
   vermont                                    (12850),  
   virginia                                   (12851),  
   virgin-Islands                             (12852),  
   washington                                 (12853),  
   west-Virginia                              (12854),  
   wisconsin                                  (12855),  
   wyoming                                    (12856),  
   -- Structures
   rest-room                                  (13057),  -- RM-140
   mens-rest-room                             (13058),  -- RA-090
   womens-rest-room                           (13059),  -- RA-100
   family-rest-room                           (13060),  -- RA-150
   dam                                        (13061),  -- RG-030
   fish-hatchery                              (13062),  -- RG-090
   information                                (13063),  -- RG-100
   lighthouse                                 (13064),  -- RG-120
   lookout-tower                              (13065),  -- RG-140
   ranger-station                             (13066),  -- RG-170
   grocery-store                              (13068),  -- RM-070
   lodging                                    (13069),  -- RM-090
   post-office                                (13070),  -- RM-110
   picnic-shelter                             (13072),  -- RM-130
   group-camping                              (13073),  -- RM-210
   group-picnicking                           (13074),  -- RM-220
   n24-hour-pharmacy                          (13075),  -- RM-230
   kennel                                     (13076),  -- RA-050
   laundry-facilities                         (13077),  -- RA-060
   shower-facilities                          (13078),  -- RA-130
   amphitheater                               (13079),  -- RL-010
   stable                                     (13080),  -- RL-080
   hospital                                   (13081),  -- D9-13a or D9-2
   emergency-medical-service-point            (13082),  -- Use for emergency medical
                                                        -- care as well D9-13c
   library                                    (13083),  -- I-8p
   recycling-collection-center                (13084),  -- I-11
   school                                     (13085),  -- Use for S1-1
   -- Street Suffixes
   alley                                      (13313),  
   annex                                      (13314),  
   arcade                                     (13315),  
   avenue                                     (13316),  
   bayoo                                      (13317),  
   beach                                      (13318),  
   bend                                       (13319),  
   bluff                                      (13320),  
   bottom                                     (13321),  
   boulevard                                  (13322),  
   branch                                     (13323),  
   nBridge                                    (13324),  -- Note use of "n" to avoid
                                                        -- conflict with other entry
   brook                                      (13325),  
   burg                                       (13326),  
   bypass                                     (13327),  
   camp                                       (13328),  
   canyon                                     (13329),  
   cape                                       (13330),  
   causeway                                   (13331),  
   nCenter                                    (13332),  --: Note use of "n" to avoid
                                                        -- conflict with other entry
   circle                                     (13333),  
   cliff                                      (13334),  
   club                                       (13335),  
   common                                     (13336),  
   corner                                     (13337),  
   course                                     (13338),  
   court                                      (13339),  
   cove                                       (13340),  
   creek                                      (13341),  
   crescent                                   (13342),  
   crest                                      (13343),  
   nCrossing                                  (13344),  -- Note use of "n" to avoid
                                                        -- conflict with other entry
   crossroad                                  (13345),  
   curve                                      (13346),  
   dale                                       (13347),  
   nDam                                       (13348),  -- Note use of "n" to avoid
                                                        -- conflict with other entry
   divide                                     (13349),  
   drive                                      (13350),  
   estate                                     (13351),  
   expressway                                 (13352),  
   extension                                  (13353),  
   fall                                       (13354),  
   nFerry                                     (13355),  -- Note use of "n" to avoid
                                                        -- conflict with other entry
   field                                      (13356),  
   flat                                       (13357),  
   ford                                       (13358),  
   forest                                     (13359),  
   forge                                      (13360),  
   fork                                       (13361),  
   fort                                       (13362),  
   nFreeway                                   (13363),  -- Note use of "n" to avoid
                                                        -- conflict with other entry
   garden                                     (13364),  
   gateway                                    (13365),  
   glen                                       (13366),  
   green                                      (13367),  
   grove                                      (13368),  
   harbor                                     (13369),  
   haven                                      (13370),  
   heights                                    (13371),  
   highway                                    (13372),  
   nHill                                      (13373),  -- Note use of "n" to avoid
                                                        -- conflict with other entry
   hollow                                     (13374),  
   inlet                                      (13375),  
   nIsland                                    (13376),  -- Note use of "n" to avoid
                                                        -- conflict with other entry
   isle                                       (13377),  --
   nJunction                                  (13378),  -- Note use of "n" to avoid
                                                        -- conflict with other entry
   key                                        (13379),  
   knoll                                      (13380),  
   lake                                       (13381),  
   land                                       (13382),  
   landing                                    (13383),  
   nLane                                      (13384),  -- Note use of "n" to avoid
                                                        -- conflict with other entry
   light                                      (13385),  
   loaf                                       (13386),  
   lock                                       (13387),  
   lodge                                      (13388),  
   loop                                       (13389),  
   mall                                       (13390),  
   manor                                      (13391),  
   meadow                                     (13392),  
   mews                                       (13393),  
   mill                                       (13394),  
   mission                                    (13395),  
   motorway                                   (13396),  
   mount                                      (13397),  
   mountain                                   (13398),  
   neck                                       (13399),  
   orchard                                    (13400),  
   oval                                       (13401),  
   nOverpass                                  (13402),  -- Note use of "n" to avoid
                                                        -- conflict with other entry
   park                                       (13403),  
   parkway                                    (13404),  
   nPass                                      (13405),  -- Note use of "n" to avoid
                                                        -- conflict with other entry
   passage                                    (13406),  
   path                                       (13407),  
   pike                                       (13408),  
   pine                                       (13409),  
   plains                                     (13410),  
   plaza                                      (13411),  
   point                                      (13412),  
   port                                       (13413),  
   prairie                                    (13414),  
   radial                                     (13415),  
   ramp                                       (13416),  
   ranch                                      (13417),  
   rapid                                      (13418),  
   rest                                       (13419),  
   ridge                                      (13420),  
   river                                      (13421),  
   nRoad                                      (13422),  -- Note use of "n" to avoid
                                                        -- conflict with other entry
   route                                      (13423),  
   row                                        (13424),  
   rue                                        (13425),  
   run                                        (13426),  
   shoal                                      (13427),  
   shore                                      (13428),  
   skyway                                     (13429),  
   spring                                     (13430),  
   nSpur                                      (13431), -- Note use of "n" to avoid
                                                        -- conflict with other entry

   square                                     (13432),  
   nStation                                   (13433),  -- Note use of "n" to avoid
                                                        -- conflict with other entry
   stravenue                                  (13434),  
   stream                                     (13435),  
   street                                     (13436),  
   summit                                     (13437),  
   terrace                                    (13438),  
   throughway                                 (13439),  
   trace                                      (13440),  
   nTrack                                     (13441),  -- Note use of "n" to avoid
                                                        -- conflict with other entry
   trafficway                                 (13442),  
   nTrail                                     (13443),  -- Note use of "n" to avoid
                                                        -- conflict with other entry
   nTunnel                                    (13444),  -- Note use of "n" to avoid
                                                        -- conflict with other entry
   turnpike                                   (13445),  
   nUnderpass                                 (13446),  -- Note use of "n" to avoid
                                                        -- conflict with other entry
   union                                      (13447),  
   valley                                     (13448),  
   viaduct                                    (13449),  
   view                                       (13450),  
   village                                    (13451),  
   ville                                      (13452),  
   vista                                      (13453),  
   nWalk                                      (13454),  -- Note use of "n" to avoid
                                                        -- conflict with other  entry
   wall                                       (13455),  
   way                                        (13456),  
   well                                       (13457),  
   -- MUTCD Locations
   -- Signage Locations
   ahead                                      (13569),  -- Location and used as
                                                        -- arrow
   here                                       (13570),  -- Location and used as
                                                        -- arrow
   here-to                                    (13571),  -- Followed by specific
                                                        -- object
   here-to-alley                              (13572),  
   here-to-corner                             (13573),  
   here-to-sign                               (13574),  
   between-signs                              (13575),  
   between                                    (13633),  -- Followed by object, and,
                                                        -- another object
   this-side-of-street                        (13576),  
   this-side-of-sign                          (13577),  
   right                                      (13579),  
   left                                       (13580),  
   begin-point                                (13581),  -- Use for "begins" as well.
                                                        -- Do not use for times/dates
   next                                       (13582),  -- May be followed by a
                                                        -- distance value
   starting-start                             (13611),  -- Do not use for
                                                        -- times/dates
   ends-end                                   (13583),  -- Do not use for
                                                        -- times/dates
   other-Side                                 (13584),  
   crossing                                   (13585),  
   crosswalks                                 (13586),  
   center-strip                               (13587),  -- Alt form: center stripe
   lane                                       (13588),  -- Used for lanes as well
   shelter                                    (13634),  -- Typically preceded by a
                                                        -- specific type
   center                                     (13635),  -- Typically preceded by a
                                                        -- specific type
   -- Signage Arrows
   hill                                       (13589),  
   both-ways-left-and-right                   (13590),  
   both-ways-45-degree-angle-tilting-right    (13591),  
   both-ways-45-degree-angle-tilting-left     (13592),  
   both-directions-of-travel                  (13593),  -- As in Centerline - left
                                                        -- turn arrows - both directions
                                                        -- of travel or for two-way
                                                        -- traffic
   left-arrow                                 (13610),  
   left-turn                                  (13594),  -- For W1R
   left-45-degree-arrow                       (13595),  
   left-45-degree-turn                        (13596),  
   ahead-and-to-the-left                      (13597),  
   ahead-and-to-the-left-at-a-45-degree-angle (13598),  
   right-arrow                                (13609),  
   right-turn                                 (13599),  -- For W1R
   right-45-degree-arrow                      (13600),  -- For W1-2
   right-45-degree-turn                       (13601),  
   ahead-and-to-the-right                     (13602),  
   ahead-and-to-the-right-at-a-45-degree-angle (13603),  
   downward-left-45-degree                    (13604),  
   downward-right-45-degree                   (13605),  
   downward-left-and-right-45-degree          (13606),  
   reverse-turn-to-right                      (13636),  -- For W1-3R
   reverse-turn-to-left                       (13637),  -- For W1-3L
   reverse-curve-to-right                     (13638),  -- For W1-4R
   reverse-curve-to-left                      (13639),  -- For W1-4L
   two-lane-reverse-curve-to-right            (13623),  -- For W1-4bR
   two-lane-reverse-curve-to-left             (13624),  -- For W1-4bL
   three-lane-reverse-curve-to-right          (13625),  -- For W1-4cR
   three-lane-reverse-curve-to-left           (13626),  -- For W1-4cL
   winding-road-to-right                      (13640),  -- For W1-5R
   winding-road-to-left                       (13641),  -- For W1-5L
   chevron-right                              (13613),  -- For W1-8R
   chevron-left                               (13614),  -- For W1-8L
   right-turn-with-junction                   (13615),  -- For horizontal alignment
                                                        -- right W1-10R
   left-turn-with-junction                    (13616),  -- For horizontal alignment
                                                        -- left W1-10L
   hairpin-right                              (13617),  -- For W1-11
   hairpin-left                               (13618),  -- For W1-11
   truck-rollover-right                       (13619),  -- For W1-13
   truck-rollover-left                        (13620),  
   n270-degree-turn-right                    (13621),  -- For W1-15
   n270-degree-turn-left                     (13622),  
   double-reverse-curve-to-right              (13627),  -- For W24-1R
   double-reverse-curve-to-left               (13628),  -- For W24-1L
   two-lane-double-reverse-curve-to-right     (13629),  -- For W24-1aR
   two-lane-double-reverse-curve-to-left      (13630),  -- For W24-1aL
   three-lane-double-reverse-curve-to-right   (13631),  -- For W24-1bR
   three-lane-double-reverse-curve-to-left    (13632)   -- For W24-1bL
   } (0..65535)


LaneRoadway ::= INTEGER  { 
   -- Lanes
   all-roadways               (8193),  -- Used as the default value
   through-lanes              (8194),  
   left-lane                  (8195),  
   right-lane                 (8196),  
   center-lane                (8197),  
   middle-lanes               (8198),  
   middle-two-lanes           (8199),  
   right-turning-lanes        (8200),  
   left-turning-lanes         (8201),  
   upper-deck-lanes           (8236),  
   lower-deck-lanes           (8237),  
   reversible-lanes           (8238),  
   right-exit-lanes           (8239),  
   left-exit-lanes            (8240),  
   right-merging-lanes        (8241),  
   left-merging-lanes         (8242),  
   -- Ramps
   right-exit-ramp            (8202),  
   right-second-exit-ramp     (8243),  
   right-entrance-ramp        (8203),  
   right-second-entrance-ramp (8245),  
   left-exit-ramp             (8204),  
   left-second-exit-ramp      (8244),  
   left-entrance-ramp         (8205),  
   left-second-entrance-ramp  (8246),  
   escape-ramp                (8234),  -- A truck feature on steep downgrades common in
                                       -- both Alaska and elsewhere.
   -- Shoulders
   hard-shoulder              (8206),  
   soft-shoulder              (8207),  
   right-shoulder             (8208),  
   left-shoulder              (8209),  
   median                     (8252),  
   sidewalk                   (8251),  
   -- Other
   highways                   (8235),  
   right-hand-parallel-lanes  (8210),  -- Alternative Rendering: right-hand frontage
                                       -- road
   left-hand-parallel-lanes   (8211),  -- Alternative Rendering: left-hand frontage road
   connecting-lanes           (8212),  
   express-lanes              (8213),  
   local-lanes                (8214),  
   toll-lanes                 (8215),  
   electronic-toll-lanes      (8216),  
   toll-plaza                 (8217),  
   inspection-lane            (8218),  -- Alternative Rendering: Border patrol
                                       -- inspection lane
   hOV-lanes                  (8219),  -- Use when 2+ or 3+ is unknown and for HOV in
                                       -- general
   bus-lanes                  (8220),  
   carpool-lanes              (8221),  
   truck-lanes                (8222),  
   emergency-lanes            (8223),  
   passing-lanes              (8224),  
   climbing-lanes             (8225),  
   slow-lane                  (8226),  -- Alternative Rendering: Crawler lane
   service-road               (8227),  -- Alternative Rendering: Frontage Road
   cycle-lane                 (8228),  -- Use for bicycle lanes of all types
   tracks                     (8250),  -- Use for light rail and transit uses, may
                                       -- have count of tracks
   -- Bridges, Tunnels
   bridge                     (8229),  
   overpass                   (8230),  
   elevated-lanes             (8231),  
   underpass                  (8232),  
   tunnel                     (8233),  -- Use for RG-200
   -- Lanes Groups
   all-exit-lanes             (8247),  
   all-entry-lanes            (8248),  
   either-shoulder            (8249),  
   shoulder-work              (8253)   -- Use for W21-5 as well
   } (0..65535)


LargeNumbers ::= INTEGER  { 
   n1-16th (11521),  -- The fraction 1/16th
   n1-10th (11522),  -- The fraction 1/10th
   n1-8th  (11523),  -- The fraction 1/8th
   n1-4th  (11524),  -- The fraction 1/4th
   n1-3rd  (11525),  -- The fraction 1/3rd
   n1-2    (11526),  -- The fraction 1/2
   n3-4    (11527),  -- The fraction 3/4th
   n300    (11531),  
   n350    (11532),  
   n400    (11533),  
   n450    (11534),  
   n500    (11535),  
   n550    (11536),  
   n600    (11537),  
   n650    (11538),  
   n700    (11539),  
   n750    (11540),  
   n800    (11541),  
   n850    (11542),  
   n900    (11543),  
   n950    (11544),  
   n1000   (11545),  
   n1100   (11546),  
   n1200   (11547),  
   n1300   (11548),  
   n1400   (11549),  
   n1500   (11550),  
   n1600   (11551),  
   n1700   (11552),  
   n1800   (11553),  
   n1900   (11554),  
   n2000   (11555),  
   n2100   (11556),  
   n2200   (11557),  
   n2300   (11558),  
   n2400   (11559),  
   n2500   (11560),  
   n2600   (11561),  
   n2700   (11562),  
   n2800   (11563),  
   n2900   (11564),  
   n3000   (11565),  
   n3500   (11566),  
   n4000   (11567),  
   n4500   (11568),  
   n5000   (11569),  
   n5500   (11570),  
   n6000   (11571),  
   n6500   (11572),  
   n7000   (11573),  
   n7500   (11574),  
   n8000   (11575),  
   n8500   (11576),  
   n9000   (11577),  
   n9500   (11578),  
   n10000  (11579),  
   n11000  (11580),  
   n12000  (11581),  
   n13000  (11582),  
   n14000  (11583),  
   n15000  (11584),  
   n16000  (11585),  
   n17000  (11586),  
   n18000  (11587),  
   n19000  (11588),  
   n20000  (11589),  
   n21000  (11590),  
   n22000  (11591),  
   n23000  (11592),  
   n24000  (11593),  
   n25000  (11594),  
   n26000  (11595),  
   n27000  (11596),  
   n28000  (11597),  
   n29000  (11598),  
   n30000  (11599),  
   n35000  (11600),  
   n40000  (11601),  
   n45000  (11602),  
   n50000  (11603),  
   n55000  (11604),  
   n60000  (11605),  
   n65000  (11606),  
   n70000  (11607),  
   n75000  (11608),  
   n80000  (11609),  
   n85000  (11610),  
   n90000  (11611),  
   n95000  (11612),  
   n100000 (11613)
   } (0..65535)


MobileSituation ::= INTEGER  { 
   abnormal-load                                   (2049),  
   wide-load                                       (2050),  
   long-load                                       (2051),  
   slow-vehicle                                    (2052),  
   farm-equipment                                  (2053),  
   horse-drawn-vehicles                            (2054),  
   overheight-load                                 (2055),  
   overweight-load                                 (2056),  
   tracked-vehicle                                 (2057),  
   vehicle-carrying-hazardous-materials            (2058),  
   slow-moving-maintenance-vehicle                 (2059),  -- Hint: mowing, line
                                                            -- stripping, sweepers, etc.
   convoy                                          (2060),  
   military-convoy                                 (2061),  
   refugee-convoy                                  (2062),  
   motorcade                                       (2063),  
   mobile-situation-repositioning                  (2064),  
   winter-maintenance-vehicles                     (2065),  
   snowplows                                       (2066),  
   -- Cancel Types
   slow-moving-maintenance-vehicle-warning-cleared (2172),  
   exceptional-load-warning-cleared                (2173),  
   hazardous-load-warning-cleared                  (2174),  
   convoy-cleared                                  (2175)
   } (0..65535)
   -- Used for events which are mobile along the network


MUTCDLocations ::= INTEGER  { 
   -- Signage Locations
   ahead                                       (13569),  -- Location and used as
                                                         -- arrow
   here                                        (13570),  -- Location and used as
                                                         -- arrow
   here-to                                     (13571),  -- Followed by specific
                                                         -- object
   here-to-alley                               (13572),  
   here-to-corner                              (13573),  
   here-to-sign                                (13574),  
   between-signs                               (13575),  
   between                                     (13633),  -- Followed by object, and,
                                                         -- another object
   this-side-of-street                         (13576),  
   this-side-of-sign                           (13577),  
   right                                       (13579),  
   left                                        (13580),  
   begin-point                                 (13581),  -- Use for "begins" as
                                                         -- well. Do not use for
                                                         -- times/dates
   next                                        (13582),  -- May be followed by a
                                                         -- distance value
   starting-start                              (13611),  -- Do not use for
                                                         -- times/dates
   ends-end                                    (13583),  -- Do not use for
                                                         -- times/dates
   other-Side                                  (13584),  
   crossing                                    (13585),  
   crosswalks                                  (13586),  
   center-strip                                (13587),  -- Alt form: center stripe
   lane                                        (13588),  -- Used for lanes as well
   shelter                                     (13634),  -- Typically preceded by a
                                                         -- specific type
   center                                      (13635),  -- Typically preceded by a
                                                         -- specific type
   -- Signage Arrows
   hill                                        (13589),  
   both-ways-left-and-right                    (13590),  
   both-ways-45-degree-angle-tilting-right     (13591),  
   both-ways-45-degree-angle-tilting-left      (13592),  
   both-directions-of-travel                   (13593),  -- As in Centerline - left
                                                         -- turn arrows - both directions
                                                         -- of travel or for two-way
                                                         -- traffic
   left-arrow                                  (13610),  
   left-turn                                   (13594),  -- For W1R
   left-45-degree-arrow                        (13595),  
   left-45-degree-turn                         (13596),  
   ahead-and-to-the-left                       (13597),  
   ahead-and-to-the-left-at-a-45-degree-angle  (13598),  
   right-arrow                                 (13609),  
   right-turn                                  (13599),  -- For W1R
   right-45-degree-arrow                       (13600),  -- For W1-2
   right-45-degree-turn                        (13601),  
   ahead-and-to-the-right                      (13602),  
   ahead-and-to-the-right-at-a-45-degree-angle (13603),  
   downward-left-45-degree                     (13604),  
   downward-right-45-degree                    (13605),  
   downward-left-and-right-45-degree           (13606),  
   reverse-turn-to-right                       (13636),  -- For W1-3R
   reverse-turn-to-left                        (13637),  -- For W1-3L
   reverse-curve-to-right                      (13638),  -- For W1-4R
   reverse-curve-to-left                       (13639),  -- For W1-4L
   two-lane-reverse-curve-to-right             (13623),  -- For W1-4bR
   two-lane-reverse-curve-to-left              (13624),  -- For W1-4bL
   three-lane-reverse-curve-to-right           (13625),  -- For W1-4cR
   three-lane-reverse-curve-to-left            (13626),  -- For W1-4cL
   winding-road-to-right                       (13640),  -- For W1-5R
   winding-road-to-left                        (13641),  -- For W1-5L
   chevron-right                               (13613),  -- For W1-8R
   chevron-left                                (13614),  -- For W1-8L
   right-turn-with-junction                    (13615),  -- For horizontal alignment
                                                         -- right W1-10R
   left-turn-with-junction                     (13616),  -- For horizontal alignment
                                                         -- left W1-10L
   hairpin-right                               (13617),  -- For W1-11
   hairpin-left                                (13618),  -- For W1-11
   truck-rollover-right                        (13619),  -- For W1-13
   truck-rollover-left                         (13620),  
   n270-degree-turn-right                     (13621),  -- For W1-15
   n270-degree-turn-left                      (13622),  
   double-reverse-curve-to-right               (13627),  -- For W24-1R
   double-reverse-curve-to-left                (13628),  -- For W24-1L
   two-lane-double-reverse-curve-to-right      (13629),  -- For W24-1aR
   two-lane-double-reverse-curve-to-left       (13630),  -- For W24-1aL
   three-lane-double-reverse-curve-to-right    (13631),  -- For W24-1bR
   three-lane-double-reverse-curve-to-left     (13632)   -- For W24-1bL
   } (0..65535)


NamedObjects ::= INTEGER  { 
   name-follows                 (11777),  -- Used for other types of named objects
                                          -- to delimit name
   freeway                      (11778),  -- Typically followed by name
   us-Route                     (11779),  -- Typically followed by name, M1-4
   state-Route                  (11780),  -- Typically followed by name, M1-5
   interstate                   (11781),  -- Typically followed by name, M1-1
   business-Loop                (11782),  -- Typically followed by name, M1-2, M4-3
   spur                         (11797),  -- Typically followed by name, M1-3
   junction                     (11798),  -- Typically followed by names, M2-1, M2-2
   alternative                  (11783),  -- Typically followed by name, M4-1, M4-1a
   county-Route                 (11784),  -- Typically followed by name, M1-6
   forest-Route                 (11785),  -- Typically followed by name, M1-7
   farm-to-Market-Route         (11786),  -- Typically followed by name
   eisenhower-Interstate-System (11787),  -- Typically followed by name, M1-10
   americas-Byways              (11788),  -- Typically followed by name, Alt term:
                                          -- National Scenic Byways
   national-Network-Route       (11789),  -- Typically followed by name
   scenic-Area                  (11790),  -- Typically followed by name
   parking-Area                 (11791),  -- Typically followed by name
   weight-Station               (11792),  -- Typically followed by name
   road                         (11793),  -- Typically followed by name (all types
                                          -- of roads and streets not otherwise listed
                                          -- above)
   exit                         (11794),  -- Typically followed by name
   historical-route             (11795),  -- Typically followed by name
   state-line                   (11796),  -- Preceded by a state name I-2
   bicycle-route                (11799),  -- Typically followed by name, M1-8
   bicycle-interstate-route     (11800),  -- Typically followed by name, M1-9
   national-park                (11801)   -- Typically preceded by name, D7-1, D7-2
   } (0..65535)


Objects ::= INTEGER  { 
   -- Misc Items
   unknown-object                 (11009),  
   tire                           (11010),  
   rim                            (11011),  
   retread                        (11012),  
   trash                          (11013),  -- Consider using the CleanUpItems of IEEE
                                            -- 1512 for operational needs
   cargo                          (11014),  
   diesel                         (11015),  
   gasoline                       (11016),  -- RM-060
   anti-freeze                    (11017),  
   propane-gas                    (11061),  
   alternative-fuel               (11060),  -- (Implies CNG)
   seat-belts                     (11018),  
   litter-container               (11019),  -- RG-130  Alt term: Trash Container
   all-Terrain-vehicle            (11020),  -- Rl-170
   seaplane                       (11021),  -- RG-260
   chairlift                      (11022),  -- RS-100
   fishing-pier                   (11023),  -- RW-160
   telephone                      (11025),  -- RM-150 See also Emergency-Telephones
                                            -- 10544
   railroad-cross-buck            (11024),  -- (Used for Railroad crossings)
   horn                           (11048),  
   train                          (11047),  -- The train itself regardless of the
                                            -- type (not the mode of transit)
   deer                           (11049),  -- W11-3
   horse                          (11051),  -- Use for equestrian as well
   cattle                         (11050),  -- W11-4
   golf-cart                      (11052),  -- W11-10
   services                       (11056),  
   motorist-services              (11059),  -- Alt text motor services D9-18
   food-services                  (11053),  
   roadside-table                 (11055),  
   ambulance-staging-point        (11054),  -- Use for ambulance station as well
   -- Shelters-Structures
   fallout                        (11026),  -- a type of shelter or structure
   medical                        (11027),  -- a type of shelter or structure
   chemical                       (11028),  -- a type of shelter or structure
   welfare                        (11029),  -- a type of shelter or structure
   decontamination                (11063),  
   evacuation                     (11030),  -- a type of shelter or structure
   registration                   (11062),  -- a type of shelter or structure
   emergency                      (11064),  --Use only when no other type is known
   -- Signal States
   left-arrow-signal              (11031),  
   ahead-arrow-signal             (11032),  
   right-arrow-signal             (11033),  
   green-light-signal             (11034),  
   green-arrow-signal             (11035),  
   yellow-light-signal            (11036),  
   yellow-arrow-signal            (11037),  
   red-light-signal               (11038),  
   red-arrow-signal               (11039),  
   extended-green-signal          (11040),  
   advance-arrow-signal           (11041),  
   pedestrian-Signal-Stop         (11042),  -- Used for donÃ¢â‚¬â„¢t walk sign
   pedestrian-Signal-Caution      (11043),  -- Used for donÃ¢â‚¬â„¢t start to walk
   pedestrian-Signal-Walk         (11044),  
   pedestrian-Signal-Light        (11045),  -- Use for light itself (regardless of
                                            -- state)
   pedestrian-Signal-Time-Display (11046)   -- Use for count down timer display
   } (0..65535)


Obstruction ::= INTEGER  { 
   -- General
   obstruction-on-roadway              (1281),  
   object-on-roadway                   (1282),  
   objects-falling-from-moving-vehicle (1283),  
   debris-on-roadway                   (1284),  
   storm-damage                        (1285),  
   -- People
   people-on-roadway                   (1286),  
   bicyclists-on-roadway               (1287),  
   sightseers-obstructing-access       (1288),  
   large-numbers-of-visitors           (1289),  
   -- Animals
   animal-on-roadway                   (1290),  
   large-animal-on-roadway             (1291),  
   herd-of-animals-on-roadway          (1292),  
   animal-struck                       (1293),  
   -- Specific Items
   advertising-signs                   (1315),  -- Used for illegal signage as well
   fallen-trees                        (1294),  
   over-turned-trees                   (1311),  
   tree-limbs                          (1312),  
   utility-pole-down                   (1314),  
   downed-power-lines                  (1295),  -- Alternative Rendering: fallen power
                                                -- lines
   downed-cables                       (1296),  -- Alternative Rendering: fallen cables
   subsidence                          (1297),  -- Alternative Rendering: road collapse
   road-surface-collapse               (1298),  
   frost-jacking                       (1317),  -- A unique Alaska problem caused by
                                                -- culverts or other features jacking out
                                                -- of ground due to freezing
   frost-heave                         (1316),  -- A large standing wave of soil under
                                                -- pavement due to frost action
   pavement-buckled                    (1299),  
   pothole                             (1300),  
   flooding                            (1301),  
   broken-water-main                   (1302),  
   collapsed-sewer                     (1303),  
   wash-out                            (1319),  -- What can happen to roads
   washboard                           (1318),  -- A term for rough road or unpaved roads
   sewer-overflow                      (1304),  
   gas-leak                            (1305),  
   snowmelt                            (1306),  -- Hint: Typically used as a cause
   mudslide                            (1307),  
   avalanche                           (1308),  -- Possibly a disaster as well
   rockfall                            (1309),  
   landslide                           (1310),  
   -- Cancel Types
   clearance-work                      (1406),  
   obstruction-cleared                 (1407)
   } (0..65535)
   -- note singular spelling


ParkingInformation ::= INTEGER  { 
   normal-parking-restrictions-lifted    (4097),  -- Hint: used when a PARKING
                                                  -- restriction is lifted (overnight
                                                  -- parking allowed during event)  Not
                                                  -- to be used as a default for this
                                                  -- category
   parking-meter-restrictions-lifted     (4098),  -- Hint: used when a METER restriction
                                                  -- is lifted (metered parking free
                                                  -- during event)
   special-parking-restrictions-in-force (4099),  
   full-parking-lot                      (4100),  
   full-parking-garage                   (4101),  
   all-parking-lots-full                 (4102),  
   no-parking-spaces-available           (4103),  
   only-a-few-spaces-available           (4104),  
   spaces-available                      (4105),  -- Typically preceded by a # value
   no-parking                            (4106),  -- Typically followed by restriction
                                                  -- data
   parking-on-one-side-of-street-only    (4107),  
   parking-on-both-sides-of-street       (4108),  
   parallel-parking-only                 (4109),  
   parking-meters-not-available          (4110),  
   use-of-parking-meters-restricted      (4111),  
   event-parking                         (4112),  
   handicapped-parking                   (4113),  
   long-term-parking                     (4114),  
   overnight-parking                     (4115),  
   short-term-parking                    (4116),  
   parking-by-permit-only                (4117),  
   emergency-parking-only                (4118),  
   emergency-stopping-only               (4119),  
   parking                               (4120),  -- Typically followed by
                                                  -- restriction data
   stopping                              (4121),  -- Typically followed by
                                                  -- restriction data
   standing                              (4122),  -- Typically followed by
                                                  -- restriction data
   tow-away-zone                         (4123),  
   school-zone                           (4124),  -- Treat as Speed Limit, with
                                                  -- details to follow
   speed-zone                            (4125),  -- Treat as Speed Limit, with
                                                  -- details to follow
   loading-zone                          (4126),  -- Typically followed by
                                                  -- restriction data
   state-law                             (4127),  
   -- Cancel Types
   van-accessible                        (4128),  
   special-parking-restrictions-lifted   (4222),  
   no-parking-information-available      (4223)
   } (0..65535)


PavementConditions ::= INTEGER  { 
   -- General
   impassable                     (5889),  
   almost-impassable              (5890),  
   passable-with-care             (5891),  
   passable                       (5892),  
   surface-water-hazard           (5893),  
   danger-of-hydroplaning         (5894),  
   wet-pavement                   (5895),  
   treated-pavement               (5896),  -- Alternative Rendering: chemical wet
   slippery                       (5897),  
   low-ground-clearance           (5938),  -- Use for W12-2 types
   at-grade-level-crossing        (5937),  
   -- On Roadway items
   mud-on-roadway                 (5898),  
   leaves-on-roadway              (5899),  
   loose-sand-on-roadway          (5900),  
   loose-gravel                   (5901),  
   fuel-on-roadway                (5902),  
   oil-on-roadway                 (5903),  
   road-surface-in-poor-condition (5904),  
   melting-tar                    (5905),  
   uneven-lanes                   (5935),  
   rough-road                     (5931),  
   rough-crossing                 (5936),  -- Typically used with grade crossings at
                                           -- rails
   -- Ice & Snow
   ice                            (5906),  
   icy-patches                    (5907),  
   black-ice                      (5908),  
   ice-pellets-on-roadway         (5909),  
   ice-build-up                   (5910),  
   freezing-rain                  (5911),  
   wet-and-icy-roads              (5912),  
   slush                          (5914),  
   melting-snow                   (5913),  
   frozen-slush                   (5915),  
   snow-on-roadway                (5916),  
   packed-snow                    (5917),  
   packed-snow-patches            (5918),  
   plowed-snow                    (5919),  
   wet-snow                       (5920),  
   fresh-snow                     (5921),  
   powder-snow                    (5922),  
   granular-snow                  (5923),  
   frozen-snow                    (5924),  
   crusted-snow                   (5925),  
   deep-snow                      (5926),  
   snow-drifts                    (5927),  
   drifting-snow                  (5928),  
   expected-snow-accumulation     (5929),  
   current-snow-accumulation      (5930),  
   -- Road Surface
   sand                           (5932),  -- Can use for W7-4d
   gravel                         (5933),  -- Can use for W7-4e
   paved                          (5934),  -- Can use for W7-4f
   -- Cancel Types
   dry-pavement                   (6011),  
   snow-cleared                   (6012),  
   pavement-conditions-improved   (6013),  
   skid-hazard-reduced            (6014),  
   pavement-conditions-cleared    (6015)
   } (0..65535)


Precipitation ::= INTEGER  { 
   severe-weather           (4865),  
   blizzard                 (4866),  
   heavy-snow               (4867),  
   snow                     (4868),  
   light-snow               (4869),  
   snow-showers             (4870),  
   winter-storm             (4871),  
   ice-glaze                (4872),  
   heavy-frost              (4873),  
   frost                    (4874),  
   ice-storm                (4875),  
   sleet                    (4876),  
   rain-and-snow-mixed      (4877),  
   rain-changing-to-snow    (4878),  
   damaging-hail            (4879),  
   hail                     (4880),  
   thunderstorms            (4881),  
   thundershowers           (4882),  
   extremely-heavy-downpour (4883),  
   heavy-rain               (4884),  
   rain                     (4885),  
   light-rain               (4886),  
   drizzle                  (4887),  
   showers                  (4888),  
   dew                      (4889),  
   -- Cancel Types
   precipitation-cleared    (4991)
   } (0..65535)


Qualifiers ::= INTEGER  { 
   -- Locations
   above                     (7681),  -- Not to be used as the default for this category
   below                     (7682),  
   in                        (7683),  
   around                    (7684),  
   after                     (7685),  
   before                    (7686),  
   at                        (7687),  -- Hint: used in conjunction with generic locations
   on                        (7688),  -- Hint: used in conjunction with "roadway" or
                                      -- other terms for both places (on-shoulder) and
                                      -- events (on-green)
   near                      (7689),  -- Hint: used with generic locations and lanes
   from-the                  (7690),  
   terminal                  (7691),  
   -- Weather Related
   falling-slowly            (7692),  
   falling                   (7693),  
   falling-quickly           (7694),  
   rising-slowly             (7695),  
   rising                    (7696),  
   rising-quickly            (7697),  
   steady                    (7698),  
   likely                    (7699),  
   changing-to               (7700),  
   mostly                    (7701),  
   partly                    (7702),  
   minus                     (7703),  
   weather-ended             (7704),  
   expected                  (7705),  
   low                       (7706),  -- Typically used in temperatures. See also "upper"
   mid                       (7707),  
   high                      (7708),  
   upper                     (7709),  -- Typically used in temperatures or broad regions. 
                                      -- See also Ã¢â‚¬Å“lowÃ¢â‚¬Â?, Ã¢â‚¬Â?midÃ¢â‚¬Â?, Ã¢â‚¬Å“highÃ¢â‚¬Â?, Ã¢â‚¬Å“middleÃ¢â‚¬Â?
   middle                    (7765),  -- Typically used for broad regions
                                      -- See also Ã¢â‚¬Å“upperÃ¢â‚¬Â?, Ã¢â‚¬Å“lowerÃ¢â‚¬Â?
   lower                     (7764),  -- Typically used for broad regions
                                      -- See also Ã¢â‚¬Å“upperÃ¢â‚¬Â?, Ã¢â‚¬Å“middleÃ¢â‚¬Â?

   unseasonably              (7710),  
   reported                  (7711),  
   -- Instructions
   advice                    (7712),  
   due-to                    (7713),  
   proceed-to                (7714),  
   transferred-to            (7715),  
   use                       (7716),  
   -- Prepositional Use
   affecting                 (7717),  
   blocking                  (7718),  
   connecting                (7719),  
   finished                  (7720),  -- Alt term: finish
   for                       (7721),  
   or                        (7722),  
   -- Other
   and                       (7723),  
   later                     (7724),  
   level                     (7725),  
   shortly                   (7726),  
   soon                      (7727),  
   service                   (7728),  
   graffiti                  (7733),  
   damaged                   (7729),  
   out-of-order              (7730),  -- See Asset Status items as well
   on-State-right-of-way     (7732),  
   found-property            (7734),  
   vandalism                 (7731),  
   major                     (7766),  
   minor                     (7767),  
   -- MUTCD Sign Usage
   begin-time                (7735),  -- Typically followed by a value entry and a
                                      -- time entry (AM/PM)
   added                     (7736),  -- Typically preceded by an object entry
   end-time                  (7737),  -- Typically followed by a value entry and a
                                      -- time entry (AM/PM)
   no                        (7738),  -- Typically followed by a value entry and
                                      -- any day/time limits
   do-not                    (7739),  -- Also used for "does not"
   block                     (7740),  -- Also used for blocks
   except                    (7741),  -- Typically followed by a value entry and a
                                      -- day/time entry
   day                       (7742),  -- Alt: daytime, daylight hours
   night                     (7743),  -- Alt: night time, night time hours
   any-time                  (7744),  -- Used also for "allowed"
   has                       (7745),  -- As in: has green (alt form: with)
   must                      (7757),  -- As in: <lane> must <turn>
   may-have                  (7746),  -- As in: may have green
   may-exceed                (7759),  -- As in: may exceed 80 mph
   only                      (7747),  
   lifted                    (7748),  -- As in gate lifted
   empty                     (7749),  
   turning                   (7750),  -- Used also for turns or turn
   u-turn                    (7751),  -- As in no u-turn allowed
   wait-for                  (7752),  
   when-flashing             (7753),  
   duration                  (7754),  -- Typically followed by a value entry and a
                                      -- time entry (Days/Hours/Min)
   cross                     (7755),  
   when-wet                  (7756),  
   oncoming                  (7758),  -- Typically followed by object or vehicle
                                      -- types
   to-request                (7760),  -- As in to request X do Y
   exempt                    (7761),  
   skewed                    (7762),  
   when-children-are-present (7763)   -- Use for S4-2
   } (0..65535)
   -- Modifiers and parts of sentences


RecreationalObjectsAndActivities ::= INTEGER  { 
   -- General Items
   bear-viewing-area             (12033),  -- RG-020
   deer-viewing-area             (12034),  -- RG-040
   drinking-water                (12035),  -- RG-050
   environmental-study-area      (12036),  -- RG-060
   falling-rocks                 (12037),  -- RG-070 See also ITIS code: Rockfall
                                           -- 1309
   firearms                      (12038),  -- RG-080
   leashed-pets                  (12039),  -- RG-110
   point-of-interest             (12040),  -- RG-160
   smoking                       (12041),  -- RG-180
   dog                           (12042),  -- RG-240
   tent-camping                  (12043),  -- RM-010
   trailer-camping               (12044),  -- RM-020
   first-aid                     (12045),  -- RM-040
   handicapped                   (12046),  -- RM-080
   mechanic                      (12047),  -- RM-100
   trailer-sanitary-station      (12048),  -- RM-160  Alt: Trailer Waste Station
   viewing-area                  (12049),  -- RM-170
   scenic-overlook               (12095),  -- For D6-2
   campfire                      (12050),  -- RA-030
   locker                        (12051),  -- RA-070
   sleeping                      (12052),  -- RA-110 As in Sleeping Shelter
   trail                         (12053),  -- RA-120 As in Trail Shelter
   climbing                      (12054),  -- RL-020
   rock-climbing                 (12055),  -- RL-030
   hunting                       (12056),  -- RL-040
   playground                    (12057),  -- RL-050
   rock-collecting               (12058),  -- RL-060
   spelunking                    (12059),  -- RL-070
   bicycle-trail                 (12060),  -- RL-090
   hiking-trail                  (12061),  -- RL-100
   horse-trail                   (12062),  -- RL-110
   trail-interpretive-auto       (12063),  -- RL-120
   trail-interpretive-pedestrian (12064),  -- RL-130
   trail-road-for-4WD-vehicles   (12065),  -- RL-140
   trail-for-trail-bikes         (12066),  -- RL-150
   archer                        (12067),  -- RL-190
   hang-glider                   (12068),  -- RL-210
   -- Water Related
   boat-tours                    (12069),  -- RW-010
   canoeing                      (12070),  -- RW-020
   diving                        (12071),  -- RW-030
   scuba-diving                  (12072),  -- RW-040
   fishing                       (12073),  -- RW-050
   marine-recreation-area        (12074),  -- RW-060
   motorboating                  (12075),  -- RW-070
   boat-ramp                     (12076),  -- RW-080
   rowboating                    (12077),  -- RW-090
   sailboating                   (12078),  -- RW-100
   water-skiing                  (12079),  -- RW-110
   surfing                       (12080),  -- RW-120
   swimming                      (12081),  -- RW-130
   wading                        (12082),  -- RW-140
   hand-launch                   (12083),  -- RW-170
   kayak                         (12084),  -- RW-190
   wind-surf                     (12085),  -- RW-210
   -- Winter-Snow Related
   ice-skating                   (12086),  -- RS-010
   ski-jumping                   (12087),  -- RS-020
   bobbing                       (12088),  -- RS-030
   cross-country-skiing          (12089),  -- RS-040
   downhill-skiing               (12090),  -- RS-050
   sledding                      (12091),  -- RS-060
   snowmobiling                  (12092),  -- RS-070
   snowshoeing                   (12093),  -- RS-080
   winter-recreation-area        (12094)   -- RS-090
   } (0..65535)


RegulatoryAndWarningSigns ::= INTEGER  { 
   -- MUTCD Signage Types
   regulatory-sign                       (12289),  -- Followed by sign data
   warning-sign                          (12290),  -- Followed by sign data
   information-sign                      (12291),  -- Followed by sign data
   construction-sign                     (12292),  -- Followed by sign data
   guide-sign                            (12293),  -- Followed by sign data
   -- MUCTD Basic Signs
   stop                                  (12294),  
   yield                                 (12295),  
   caution                               (12330),  
   temporary                             (12331),  
   to-oncoming-traffic                   (12296),  
   four-way                              (12297),  -- As in 4-way stop
   all-way                               (12298),  -- All directions of travel
                                                   -- allowed or all lanes at a junction
   one-way                               (12329),  -- One direction of travel
                                                   -- allowed
   -- MUCTD Sign Fragments
   zone                                  (12299),  -- Typically preceded by type of
                                                   -- zone
   narrows                               (12300),  -- Used as an MUTCD sign,
                                                   -- typically preceded by road
   widens                                (12301),  -- Used as an MUTCD sign,
                                                   -- typically preceded by road
   reduced                               (12302),  -- Used as an MUTCD sign,
                                                   -- typically preceded by road or lane
   combined                              (12303),  
   minimum                               (12304),  
   maximum                               (12305),  
   divided-road                          (12306),  -- Use for divided highway as
                                                   -- well
   double-arrow                          (12307),  
   dead-end                              (12308),  
   no-outlet                             (12309),  
   wrong-way                             (12310),  -- R-5-1a
   do-not-enter                          (12314),  -- R-5-1
   nDetour                               (12312),  -- Typically followed by arrows
                                                   -- and distance
   chevron                               (12313),  
   -- MUCTD Intersection Graphics
   t-intersection-to-the-side            (12315),  
   t-intersection-oncoming               (12316),  -- Use for W2-4 graphic
   y-intersection-to-the-side            (12317),  
   y-intersection-oncoming               (12318),  -- Use for W2-5 graphic
   four-way-divided-highway-crossing     (12319),  -- Use for R6-3 graphic
   t-way-divided-highway-crossing        (12320),  -- Use for R6-3a graphic
   light-rail-divided-highway-crossing   (12321),  -- Use for R15-7 graphic
   light-rail-t-divided-highway-crossing (12322),  -- Use for R15-7a graphic
   side-road-to-right                    (12323),  -- Use for W2-2R graphic
   side-road-to-left                     (12324),  -- Use for W2-2L graphic
   side-road-to-right-at-angle           (12325),  -- Use for W2-3R graphic
   side-road-to-left-at-angle            (12326),  -- Use for W2-3L graphic
   entering-roadway-merge                (12327),  -- Use for W4-5 graphic
   entering-roadway-added-lane           (12328)   -- Use for W4-6 graphic
   } (0..65535)


ResponderGroupAffected ::= INTEGER  { 
   emergency-vehicle-units           (9729),  -- Default phrase, to be used when one of
                                              -- the below does not fit better
   federal-law-enforcement-units     (9730),  
   state-police-units                (9731),  
   county-police-units               (9732),  -- Hint: also sheriff response units
   local-police-units                (9733),  
   ambulance-units                   (9734),  
   rescue-units                      (9735),  
   fire-units                        (9736),  
   hAZMAT-units                      (9737),  -- Any vehicle assigned to HAZMAT duties
   light-tow-unit                    (9738),  
   heavy-tow-unit                    (9739),  
   private-tow-units                 (9743),  -- For 3rd Party tow trucks
   freeway-service-patrols           (9740),  
   transportation-response-units     (9741),  
   private-contractor-response-units (9742)
   } (0..65535)
   -- These groups are used in coordinated response and staging area information
   -- (rather than typically consumer related)


RestrictionClass ::= INTEGER  { 
   restrictions                                     (2561),  
   ramp-restrictions                                (2562),  
   truck-restriction                                (2563),  
   speed-restriction                                (2564),  -- Used for required speeds,
                                                             -- not advised speeds
   noise-restriction                                (2565),  
   traffic-regulations-have-been-changed            (2566),  
   local-access-only                                (2567),  
   no-trailers                                      (2568),  
   no-high-profile-vehicles                         (2569),  
   hazardous-materials-truck-restriction            (2570),  
   no-through-traffic                               (2571),  
   no-motor-vehicles                                (2572),  
   width-limit                                      (2573),  -- Typically followed by a
                                                             -- number and unit value
   height-limit                                     (2574),  -- Typically followed by a
                                                             -- number and unit value
   length-limit                                     (2575),  -- Typically followed by a
                                                             -- number and unit value
   axle-load-limit                                  (2576),  -- Typically followed by a
                                                             -- number and unit value
   gross-weight-limit                               (2577),  -- Typically followed by a
                                                             -- number and unit value
   axle-count-limit                                 (2578),  -- Typically followed by a
                                                             -- number and unit value
   carpool-lane-available                           (2579),  
   carpool-restrictions-changed                     (2580),  
   hOV-2-no-single-occupant-vehicles                (2581),  
   hOV-3-no-vehicles-with-less-than-three-occupants (2582),  
   bus-lane-available-for-all-vehicles              (2583),  
   truck-lane-available-for-all-vehicles            (2584),  
   permits-call-in-basis                            (2585),  
   permits-temporarily-closed                       (2586),  
   permits-closed                                   (2587),  
   road-use-permits-required                        (2588),  
   -- Cancel Types
   permits-open                                     (2675),  
   restrictions-for-high-profile-vehicles-lifted    (2676),  
   width-limit-lifted                               (2677),  
   height-limit-lifted                              (2678),  
   length-limit-lifted                              (2679),  
   axle-load-limit-lifted                           (2680),  
   weight-limit-lifted                              (2681),  
   axle-count-limit-lifted                          (2682),  
   carpool-restrictions-lifted                      (2683),  
   lane-restrictions-lifted                         (2684),  
   ramp-restrictions-lifted                         (2685),  
   motor-vehicle-restrictions-lifted                (2686),  
   restrictions-lifted                              (2687)
   } (0..65535)


RoadsideAssets ::= INTEGER  { 
   -- Inanimate Objects
   none                        (10496),  -- Implies free text follows
   light-pole                  (10497),  
   utility-pole                (10498),  
   gantry-way                  (10499),  
   sign-support                (10500),  -- All forms of signage
   signal-pole                 (10501),  
   signage-public              (10502),  
   signage-private             (10503),  
   overhead-sign               (10568),  
   ground-sign                 (10569),  
   cones                       (10504),  -- Typical std height cones as per MUTCD
   cones-post-type             (10505),  -- Also called channelizer cones or delineator
                                         -- posts
   cones-glue-post             (10506),  -- For all glue-down types
   cones-other                 (10507),  -- Specialty types or misc. smaller cones
   barriers                    (10508),  
   barrier-Aframe              (10509),  -- Sizes larger than 1.5 meters in length
   barriers-heavy-duty         (10510),  -- All types requiring equipment to place
   barricade-type-III          (10511),  -- All collapsible Type III Barricades
   barricade-small             (10512),  -- Type I and all small A frame types, also
                                         -- so-called "mini" or "narrows" types
   solid-barrier               (10565),  
   moveable-barrier            (10566),  
   barricade-lights            (10513),  -- Std 7" light as per ITE stds
   beacon                      (10514),  -- All types of strobe and rotating lights
   t-stand                     (10515),  
   a-stand                     (10516),  
   drums                       (10517),  -- Common drums and barrel types
   sand-barrel                 (10567),  
   impact-attenuator           (10518),  -- Water-filled and other crushable types
   barricade-tape              (10519),  -- Lettering type (legend) to be conveyed
                                         -- elsewhere
   safety-fence                (10520),  
   temp-pavement-markings      (10521),  -- All forms of temp markings
   speed-bumps                 (10522),  -- Use also for speed humps
   temp-curbs                  (10523),  
   parking-blocks              (10524),  
   signboard-fixed             (10525),  
   signboard-portable          (10526),  
   stripe                      (10572),  
   island                      (10573),  -- Used for raised islands in median
   -- Controllable or Active Objects
   har                         (10527),  -- Transmission type not known
   har-AM                      (10528),  
   har-FM                      (10529),  
   har-DSRC                    (10530),  
   traffic-light               (10531),  -- Also used for signalized intersections
   lane-control-signal         (10532),  
   traffic-detector            (10533),  
   vehicle-detector            (10534),  
   system-alarm                (10535),  
   arrow-board                 (10536),  
   fixed-VMS                   (10537),  
   mobile-VMS                  (10538),  
   ramp-control                (10539),  
   gate-control                (10540),  -- Other than rail types
   temporary-traffic-light     (10541),  
   over-height-warning-system  (10542),  
   over-weight-warning-system  (10543),  
   emergency-telephones        (10544),  
   railroad-crossing-equipment (10545),  
   tunnel-ventilation          (10546),  -- Use also for fans
   ccTV                        (10547),  
   environmental-sensor        (10548),  
   emergency-signal            (10570),  
   countdown-pedestrian-sign   (10571),  
   -- Items Used by Rail and Transit
   switch                      (10549),  -- In the context of a railroad device
   signal                      (10550),  -- In the context of a railroad device
   third-rail                  (10551),  
   overhead-power              (10552),  -- Specifically the power feed line for a
                                         -- vehicle, do not use for general power lines
   concrete-tie                (10553),  
   wooden-tie                  (10554),  
   manhole-cover               (10559),  
   -- Misc. Items
   culvert                     (10560),  
   escalator                   (10555),  
   elevator                    (10556),  
   snow-poles                  (10561),  -- A tall pole and overhanging arm (like a
                                         -- luminaire) with reflective markers to help
                                         -- indicate roadway in mountain passes during
                                         -- whiteout conditions
   track                       (10557),  
   guide-poles                 (10562),  -- Poles along road to indicate guard rail in
                                         -- deep snow
   drawbridge                  (10558),  
   expansion-joint             (10563),  
   shifted-plate               (10564)
   } (0..65535)


Roadwork ::= INTEGER  { 
   -- Roads
   road-construction                          (1025),  -- Alt text: Road Work
   major-road-construction                    (1026),  
   long-term-road-construction                (1027),  
   construction-work                          (1028),  
   paving-operations                          (1029),  
   work-in-the-median                         (1030),  
   road-reconstruction                        (1031),  
   opposing-traffic                           (1032),  
   narrow-lanes                               (1033),  
   construction-traffic-merging               (1034),  
   single-line-traffic-alternating-directions (1035),  
   road-maintenance-operations                (1036),  
   road-marking-operations                    (1037),  
   road-widening                              (1061),  -- Used for roadwork, not as an
                                                       -- MUTCD sign
   cracks                                     (1052),  -- Used for disjoint roadway
                                                       -- surface
   crack-REMOVE                               (1058),  -- No Longer Used. Used for
                                                       -- disjoint roadway surface
   bumps                                      (1053),  -- Used for swelling
   drop-off                                   (1059),  
   storm-drain                                (1054),  
   -- Bridges
   bridge-maintenance-operations              (1038),  
   bridge-construction                        (1039),  
   bridge-demolition-work                     (1040),  
   seismic-retrofit                           (1060),  -- All types of earthquake
                                                       -- construction
   -- Other
   overgrown-grass                            (1055),  
   overgrown-brushshrubs                      (1056),  
   overgrown-trees                            (1057),  
   blasting                                   (1041),  -- See also: avalanche
   avalanche-control-activities               (1042),  
   water-main-work                            (1043),  
   gas-main-work                              (1044),  
   work-on-underground-cables                 (1045),  
   work-on-underground-services               (1046),  
   new-road-construction-layout               (1047),  
   new-road-layout                            (1048),  
   temporary-lane-markings                    (1049),  
   temporary-traffic-lights                   (1050),  
   emergency-maintenance                      (1051),  
   utility-work                               (1062),  
   -- Cancel Types
   road-maintenance-cleared                   (1146),  
   normal-road-layout-restored                (1147),  
   road-work-clearance-in-progress            (1148),  
   road-construction-cleared                  (1149),  
   normal-traffic-lanes-restored              (1150),  
   road-work-cleared                          (1151)
   } (0..65535)


SmallNumbers ::= INTEGER  { 
   n1   (12545),  
   n2   (12546),  
   n3   (12547),  
   n4   (12548),  
   n5   (12549),  
   n6   (12550),  
   n7   (12551),  
   n8   (12552),  
   n9   (12553),  
   n10  (12554),  
   n11  (12555),  
   n12  (12556),  
   n13  (12557),  
   n14  (12558),  
   n15  (12559),  
   n16  (12560),  
   n17  (12561),  
   n18  (12562),  
   n19  (12563),  
   n20  (12564),  
   n21  (12565),  
   n22  (12566),  
   n23  (12567),  
   n24  (12568),  
   n25  (12569),  
   n26  (12570),  
   n27  (12571),  
   n28  (12572),  
   n29  (12573),  
   n30  (12574),  
   n31  (12575),  
   n32  (12576),  
   n33  (12577),  
   n34  (12578),  
   n35  (12579),  
   n36  (12580),  
   n37  (12581),  
   n38  (12582),  
   n39  (12583),  
   n40  (12584),  
   n41  (12585),  
   n42  (12586),  
   n43  (12587),  
   n44  (12588),  
   n45  (12589),  
   n46  (12590),  
   n47  (12591),  
   n48  (12592),  
   n49  (12593),  
   n50  (12594),  
   n51  (12595),  
   n52  (12596),  
   n53  (12597),  
   n54  (12598),  
   n55  (12599),  
   n56  (12600),  
   n57  (12601),  
   n58  (12602),  
   n59  (12603),  
   n60  (12604),  
   n61  (12605),  
   n62  (12606),  
   n63  (12607),  
   n64  (12608),  
   n65  (12609),  
   n66  (12610),  
   n67  (12611),  
   n68  (12612),  
   n69  (12613),  
   n70  (12614),  
   n71  (12615),  
   n72  (12616),  
   n73  (12617),  
   n74  (12618),  
   n75  (12619),  
   n76  (12620),  
   n77  (12621),  
   n78  (12622),  
   n79  (12623),  
   n80  (12624),  
   n81  (12625),  
   n82  (12626),  
   n83  (12627),  
   n84  (12628),  
   n85  (12629),  
   n86  (12630),  
   n87  (12631),  
   n88  (12632),  
   n89  (12633),  
   n90  (12634),  
   n91  (12635),  
   n92  (12636),  
   n93  (12637),  
   n94  (12638),  
   n95  (12639),  
   n96  (12640),  
   n97  (12641),  
   n98  (12642),  
   n99  (12643),  
   n100 (12644),  
   n101 (12645),  
   n102 (12646),  
   n103 (12647),  
   n104 (12648),  
   n105 (12649),  
   n106 (12650),  
   n107 (12651),  
   n108 (12652),  
   n109 (12653),  
   n110 (12654),  
   n111 (12655),  
   n112 (12656),  
   n113 (12657),  
   n114 (12658),  
   n115 (12659),  
   n116 (12660),  
   n117 (12661),  
   n118 (12662),  
   n119 (12663),  
   n120 (12664),  
   n121 (12665),  
   n122 (12666),  
   n123 (12667),  
   n124 (12668),  
   n125 (12669),  
   n126 (12670),  
   n127 (12671),  
   n128 (12672),  
   n129 (12673),  
   n130 (12674),  
   n131 (12675),  
   n132 (12676),  
   n133 (12677),  
   n134 (12678),  
   n135 (12679),  
   n136 (12680),  
   n137 (12681),  
   n138 (12682),  
   n139 (12683),  
   n140 (12684),  
   n141 (12685),  
   n142 (12686),  
   n143 (12687),  
   n144 (12688),  
   n145 (12689),  
   n146 (12690),  
   n147 (12691),  
   n148 (12692),  
   n149 (12693),  
   n150 (12694),  
   n151 (12695),  
   n152 (12696),  
   n153 (12697),  
   n154 (12698),  
   n155 (12699),  
   n156 (12700),  
   n157 (12701),  
   n158 (12702),  
   n159 (12703),  
   n160 (12704),  
   n161 (12705),  
   n162 (12706),  
   n163 (12707),  
   n164 (12708),  
   n165 (12709),  
   n166 (12710),  
   n167 (12711),  
   n168 (12712),  
   n169 (12713),  
   n170 (12714),  
   n171 (12715),  
   n172 (12716),  
   n173 (12717),  
   n174 (12718),  
   n175 (12719),  
   n176 (12720),  
   n177 (12721),  
   n178 (12722),  
   n179 (12723),  
   n180 (12724),  
   n181 (12725),  
   n182 (12726),  
   n183 (12727),  
   n184 (12728),  
   n185 (12729),  
   n186 (12730),  
   n187 (12731),  
   n188 (12732),  
   n189 (12733),  
   n190 (12734),  
   n191 (12735),  
   n192 (12736),  
   n193 (12737),  
   n194 (12738),  
   n195 (12739),  
   n196 (12740),  
   n197 (12741),  
   n198 (12742),  
   n199 (12743),  
   n200 (12744),  
   n201 (12745),  
   n202 (12746),  
   n203 (12747),  
   n204 (12748),  
   n205 (12749),  
   n206 (12750),  
   n207 (12751),  
   n208 (12752),  
   n209 (12753),  
   n210 (12754),  
   n211 (12755),  
   n212 (12756),  
   n213 (12757),  
   n214 (12758),  
   n215 (12759),  
   n216 (12760),  
   n217 (12761),  
   n218 (12762),  
   n219 (12763),  
   n220 (12764),  
   n221 (12765),  
   n222 (12766),  
   n223 (12767),  
   n224 (12768),  
   n225 (12769),  
   n226 (12770),  
   n227 (12771),  
   n228 (12772),  
   n229 (12773),  
   n230 (12774),  
   n231 (12775),  
   n232 (12776),  
   n233 (12777),  
   n234 (12778),  
   n235 (12779),  
   n236 (12780),  
   n237 (12781),  
   n238 (12782),  
   n239 (12783),  
   n240 (12784),  
   n241 (12785),  
   n242 (12786),  
   n243 (12787),  
   n244 (12788),  
   n245 (12789),  
   n246 (12790),  
   n247 (12791),  
   n248 (12792),  
   n249 (12793),  
   n250 (12794),  
   n251 (12795),  
   n252 (12796),  
   n253 (12797),  
   n254 (12798),  
   n255 (12799)
   } (0..65535)


SpecialEvents ::= INTEGER  { 
   major-event            (3841),  
   airshow                (3842),  
   hot-air-ballooning     (3843),  
   concert                (3844),  
   state-occasion         (3845),  
   vIP-visit              (3846),  
   show                   (3847),  
   festival               (3848),  -- Used for farmers' markets as well
   exhibition             (3849),  
   performing-arts        (3850),  
   outdoor-market         (3851),  -- Used for farmers' markets as well
   fair                   (3852),  
   carnival               (3853),  
   fireworks-display      (3854),  
   trade-expo             (3855),  
   movie-filming          (3856),  
   presidential-visit     (3857),  
   parade                 (3858),  
   procession             (3859),  
   funeral-procession     (3860),  
   crowd                  (3861),  
   holiday-traffic-crowds (3862),  
   -- Cancel Types
   event-ended            (3967)
   } (0..65535)
   -- Events which affect the local roads


SportingEvents ::= INTEGER  { 
   sports-event          (3585),  
   game                  (3586),  
   tournament            (3587),  
   track-and-field-event (3588),  
   baseball-game         (3589),  
   basketball-game       (3590),  
   boxing-match          (3591),  
   football-game         (3592),  
   soccer-game           (3593),  
   golf-tournament       (3594),  
   hockey-game           (3595),  
   tennis-tournament     (3596),  
   wrestling-match       (3597),  
   road-race             (3598),  -- Hint: used for motorcycle races as well
   automobile-race       (3599),  
   bicycle-race          (3600),  
   race-event            (3601),  
   marathon              (3602),  
   horse-show            (3603),  
   rodeo                 (3604),  
   water-sports-event    (3605),  
   winter-sports-event   (3606),  
   skating-event         (3607),  
   dog-sled-race         (3608),  
   -- Cancel Types
   sporting-event-ended  (3711)
   } (0..65535)
   -- Events occurring on or nearby the roadway


StatesAndTerritories ::= INTEGER  { 
   alabama                   (12801),  
   alaska                    (12802),  
   american-Samoa            (12803),  
   arizona                   (12804),  
   arkansas                  (12805),  
   california                (12806),  
   colorado                  (12807),  
   connecticut               (12808),  
   delaware                  (12809),  
   district-of-Columbia      (12810),  
   florida                   (12811),  
   georgia                   (12812),  
   guam                      (12813),  
   hawaii                    (12814),  
   idaho                     (12815),  
   illinois                  (12816),  
   indiana                   (12817),  
   iowa                      (12818),  
   kansas                    (12819),  
   kentucky                  (12820),  
   louisiana                 (12821),  
   maine                     (12822),  
   maryland                  (12823),  
   massachusetts             (12824),  
   michigan                  (12825),  
   minnesota                 (12826),  
   mississippi               (12827),  
   missouri                  (12828),  
   montana                   (12829),  
   nebraska                  (12830),  
   nevada                    (12831),  
   new-Hampshire             (12832),  
   new-Jersey                (12833),  
   new-Mexico                (12834),  
   new-York                  (12835),  
   north-Carolina            (12836),  
   north-Dakota              (12837),  
   northern-Marianas-Islands (12838),  
   ohio                      (12839),  
   oklahoma                  (12840),  
   oregon                    (12841),  
   pennsylvania              (12842),  
   puerto-rico               (12843),  
   rhode-Island              (12844),  
   south-Carolina            (12845),  
   south-Dakota              (12846),  
   tennessee                 (12847),  
   texas                     (12848),  
   utah                      (12849),  
   vermont                   (12850),  
   virginia                  (12851),  
   virgin-Islands            (12852),  
   washington                (12853),  
   west-Virginia             (12854),  
   wisconsin                 (12855),  
   wyoming                   (12856)
   } (0..65535)


StreetSuffixes ::= INTEGER  { 
   alley      (13313),  
   annex      (13314),  
   arcade     (13315),  
   avenue     (13316),  
   bayoo      (13317),  
   beach      (13318),  
   bend       (13319),  
   bluff      (13320),  
   bottom     (13321),  
   boulevard  (13322),  
   branch     (13323),  
   nBridge    (13324),  -- Note use of "n" to avoid conflict with other entry
   brook      (13325),  
   burg       (13326),  
   bypass     (13327),  
   camp       (13328),  
   canyon     (13329),  
   cape       (13330),  
   causeway   (13331),  
   nCenter    (13332),  -- Note use of "n" to avoid conflict with other entry
   circle     (13333),  
   cliff      (13334),  
   club       (13335),  
   common     (13336),  
   corner     (13337),  
   course     (13338),  
   court      (13339),  
   cove       (13340),  
   creek      (13341),  
   crescent   (13342),  
   crest      (13343),  
   nCrossing  (13344),  -- Note use of "n" to avoid conflict with other entry
   crossroad  (13345),  
   curve      (13346),  
   dale       (13347),  
   nDam       (13348),  -- Note use of "n" to avoid conflict with other entry
   divide     (13349),  
   drive      (13350),  
   estate     (13351),  
   expressway (13352),  
   extension  (13353),  
   fall       (13354),  
   nFerry     (13355),  -- Note use of "n" to avoid conflict with other entry
   field      (13356),  
   flat       (13357),  
   ford       (13358),  
   forest     (13359),  
   forge      (13360),  
   fork       (13361),  
   fort       (13362),  
   nFreeway   (13363),  -- Note use of "n" to avoid conflict with other entry
   garden     (13364),  
   gateway    (13365),  
   glen       (13366),  
   green      (13367),  
   grove      (13368),  
   harbor     (13369),  
   haven      (13370),  
   heights    (13371),  
   highway    (13372),  
   nHill      (13373),  -- Note use of "n" to avoid conflict with other entry
   hollow     (13374),  
   inlet      (13375),  
   nIsland    (13376),  -- Note use of "n" to avoid conflict with other entry
   isle       (13377),  
   nJunction  (13378),  -- Note use of "n" to avoid conflict with other entry
   key        (13379),  
   knoll      (13380),  
   lake       (13381),  
   land       (13382),  
   landing    (13383),  
   nLane      (13384),  -- Note use of "n" to avoid conflict with other entry
   light      (13385),  
   loaf       (13386),  
   lock       (13387),  
   lodge      (13388),  
   loop       (13389),  
   mall       (13390),  
   manor      (13391),  
   meadow     (13392),  
   mews       (13393),  
   mill       (13394),  
   mission    (13395),  
   motorway   (13396),  
   mount      (13397),  
   mountain   (13398),  
   neck       (13399),  
   orchard    (13400),  
   oval       (13401),  
   nOverpass  (13402),  -- Note use of "n" to avoid conflict with other entry
   park       (13403),  
   parkway    (13404),  
   nPass      (13405),  -- Note use of "n" to avoid conflict with other entry
   passage    (13406),  
   path       (13407),  
   pike       (13408),  
   pine       (13409),  
   plains     (13410),  
   plaza      (13411),  
   point      (13412),  
   port       (13413),  
   prairie    (13414),  
   radial     (13415),  
   ramp       (13416),  
   ranch      (13417),  
   rapid      (13418),  
   rest       (13419),  
   ridge      (13420),  
   river      (13421),  
   nRoad      (13422),  -- Note use of "n" to avoid conflict with other entry
   route      (13423),  
   row        (13424),  
   rue        (13425),  
   run        (13426),  
   shoal      (13427),  
   shore      (13428),  
   skyway     (13429),  
   spring     (13430),  
   nSpur      (13431),  -- Note use of "n" to avoid conflict with other entry 
   square     (13432),  
   nStation   (13433),  -- Note use of "n" to avoid conflict with other entry
   stravenue  (13434),  
   stream     (13435),  
   street     (13436),  
   summit     (13437),  
   terrace    (13438),  
   throughway (13439),  
   trace      (13440),  
   nTrack     (13441),  -- Note use of "n" to avoid conflict with other entry
   trafficway (13442),  
   nTrail     (13443),  -- Note use of "n" to avoid conflict with other entry
   nTunnel    (13444),  -- Note use of "n" to avoid conflict with other entry
   turnpike   (13445),  
   nUnderpass (13446),  -- Note use of "n" to avoid conflict with other entry
   union      (13447),  
   valley     (13448),  
   viaduct    (13449),  
   view       (13450),  
   village    (13451),  
   ville      (13452),  
   vista      (13453),  
   nWalk      (13454),  -- Note use of "n" to avoid conflict with other  entry
   wall       (13455),  
   way        (13456),  
   well       (13457)
   } (0..65535)


Structures ::= INTEGER  { 
   rest-room                       (13057),  -- RM-140
   mens-rest-room                  (13058),  -- RA-090
   womens-rest-room                (13059),  -- RA-100
   family-rest-room                (13060),  -- RA-150
   dam                             (13061),  -- RG-030
   fish-hatchery                   (13062),  -- RG-090
   information                     (13063),  -- RG-100
   lighthouse                      (13064),  -- RG-120
   lookout-tower                   (13065),  -- RG-140
   ranger-station                  (13066),  -- RG-170
   grocery-store                   (13068),  -- RM-070
   lodging                         (13069),  -- RM-090
   post-office                     (13070),  -- RM-110
   picnic-shelter                  (13072),  -- RM-130
   group-camping                   (13073),  -- RM-210
   group-picnicking                (13074),  -- RM-220
   n24-hour-pharmacy               (13075),  -- RM-230
   kennel                          (13076),  -- RA-050
   laundry-facilities              (13077),  -- RA-060
   shower-facilities               (13078),  -- RA-130
   amphitheater                    (13079),  -- RL-010
   stable                          (13080),  -- RL-080
   hospital                        (13081),  -- D9-13a or D9-2
   emergency-medical-service-point (13082),  -- Use for emergency medical care as
                                             -- well D9-13c
   library                         (13083),  -- I-8p
   recycling-collection-center     (13084),  -- I-11
   school                          (13085)   -- Use for S1-1
   } (0..65535)


SuggestionAdvice ::= INTEGER  { 
   why-not-ride-share                         (6657),  
   is-this-your-no-ride-day                   (6658),  
   why-not-use-transit                        (6659),  
   why-not-park-and-ride                      (6660),  
   why-not-try-paratransit                    (6661),  
   why-not-travel-by-rail                     (6662),  
   why-not-use-the-subway                     (6663),  
   why-not-try-rapid-transit                  (6664),  
   why-not-travel-by-bus                      (6665),  
   your-parking-ticket-covers-the-return-ride (6666),  
   avoid-the-rush-hour                        (6667),  
   do-not-allow-unnecessary-gaps              (6668),  
   follow-the-vehicle-in-front-smoothly       (6669),  
   do-not-slow-down-unnecessarily             (6670),  
   watch-for-muggers                          (6671),  
   watch-for-pickpockets                      (6672),  
   watch-for-thieves                          (6673),  
   sorry-for-any-delay                        (6674),  
   thank-you-for-your-understanding           (6675),  
   we-appreciate-your-patience                (6676),  
   we-are-grateful-for-your-cooperation       (6677),  
   share-the-road                             (6678)
   } (0..65535)


Temperature ::= INTEGER  { 
   maximum-temperature                     (5633),  -- This index is not to be used as a
                                                    -- default value for this category
   temperature                             (5634),  -- Typically followed by a number
                                                    -- value and a unit value
   minimum-temperature                     (5635),  
   current-temperature                     (5636),  
   heat-index                              (5637),  
   extreme-heat                            (5638),  
   hot                                     (5639),  
   hotter                                  (5640),  
   heat                                    (5641),  
   warmer                                  (5642),  
   warm                                    (5643),  
   mild                                    (5644),  
   cool                                    (5645),  
   cooler                                  (5646),  
   cold                                    (5647),  
   colder                                  (5648),  
   very-cold                               (5649),  
   extreme-cold                            (5650),  
   wind-chill                              (5651),  
   dewpoint                                (5652),  
   relative-humidity                       (5653),  
   -- Cancel Types
   temperatures-close-to-the-seasonal-norm (5758),  
   less-extreme-temperatures               (5759)
   } (0..65535)


TrafficConditions ::= INTEGER  { 
   stopped-traffic                  (257),  
   stop-and-go-traffic              (258),  
   slow-traffic                     (259),  
   heavy-traffic                    (260),  
   traffic-building                 (261),  
   long-queues                      (262),  
   traffic-congestion               (263),  
   traffic-lighter-than-normal      (264),  
   traffic-heavier-than-normal      (265),  
   traffic-much-heavier-than-normal (266),  
   current-speed                    (267),  -- Typically followed by a value entry and a
                                            -- units entry (MPH/KPH)
   speed-limit                      (268),  -- Typically followed by a value entry and a
                                            -- units entry (MPH/KPH)
   travel-time                      (269),  -- Typically followed by a value entry and a
                                            -- units entry (seconds)
   merging-traffic                  (272),  -- Typically followed by direction
                                            -- left/right. Can be used for W4-1R and
                                            -- W4-1L signs
   contraflow                       (273),  
   -- Cancel Types
   contraflow-canceled              (378),  
   traffic-flowing-freely           (379),  
   traffic-easing                   (380),  -- Alternative rendering: traffic clearing
   traffic-returned-to-normal       (381),  
   no-problems-to-report            (382),  
   traffic-congestion-cleared       (383)
   } (0..65535)


TransitMode ::= INTEGER  { 
   travel             (8961),  -- Hint: may include all modes
   transit            (8962),  -- Hint: may include all public transit modes
   bus                (8963),  
   trolleybus         (8964),  
   rail               (8965),  
   commuter-rail      (8966),  
   subway             (8967),  
   rapid-transit      (8968),  
   light-rail         (8969),  
   streetcar          (8970),  -- Alternative Rendering: tram
   dial-a-ride        (8971),  -- Alternative Rendering: demand responsive transit
   park-and-ride      (8972),  -- Not to be used as a place
   shuttle            (8973),  
   free-shuttle       (8974),  -- Alternative Rendering: tram
   airport-shuttle    (8975),  
   taxies             (8976),  
   ferry              (8977),  
   passenger-ferry    (8978),  
   vehicle-ferry      (8979),  
   aerial-tramway     (8980),  
   automated-guideway (8981),  -- Include all types of guideways
   cable-cars         (8982),  
   monorail           (8983),  
   air-travel         (8984),  -- All modes of air travel
   hitch-hitching     (8985),  
   walk               (8986)   -- Alt form: Walking
   } (0..65535)
   -- Used to describe various types of transit services, and information pertaining
   -- to the whole mode. If you wish to identify a specific vehicle (such as a bus not
   -- the bus fleet), use Vehicle Group


TransitOperations ::= INTEGER  { 
   unknown-transit-problem                       (10753),  
   sleeping-customer                             (10754),  
   assault-on-passenger                          (10755),  
   assault-on-employee                           (10756),  
   broken-seat                                   (10757),  
   bus-alarm                                     (10758),  
   crime-or-drug-deal                            (10759),  
   eating-on-board                               (10760),  
   equipment-problem-with-air-conditioning       (10761),  
   equipment-problem-with-air-system             (10762),  
   equipment-problem-with-brakes                 (10763),  
   equipment-problem-with-chassis-or-suspension  (10764),  
   equipment-problem-with-cooling-system         (10765),  
   equipment-problem-with-doors                  (10766),  
   equipment-problem-with-electrical             (10767),  
   equipment-problem-with-engine                 (10768),  
   equipment-problem-with-exterior-or-body       (10769),  
   equipment-problem-with-fare-collection        (10770),  
   equipment-problem-with-fuel-or-exhaust        (10771),  
   equipment-problem-with-horn                   (10772),  
   equipment-problem-with-interior               (10773),  
   equipment-problem-with-liftkneeling           (10774),  
   equipment-problem-with-lights                 (10775),  
   equipment-problem-with-lubrication            (10776),  
   equipment-problem-with-radio-or-communication (10777),  
   equipment-problem-with-signs                  (10778),  
   equipment-problem-with-steering               (10779),  
   equipment-problem-with-tires                  (10780),  
   equipment-problem-with-transmission           (10781),  
   equipment-problem-with-unknown-alarm          (10782),  
   equipment-problem-with-wipers                 (10783),  
   fare-dispute-expired-pass                     (10784),  
   fare-dispute-expired-transfer                 (10785),  
   fare-dispute-expired-upgrade                  (10786),  
   fare-dispute-other                            (10787),  
   fare-dispute-refuses-to-pay                   (10788),  
   lift-passenger-cycle-completed                (10789),  
   lift-passenger-ready-to-alight                (10790),  
   lift-passenger-ready-to-board                 (10791),  
   lost-article                                  (10792),  
   objects-thrown                                (10793),  
   passenger-accident-alighting                  (10794),  
   passenger-accident-boarding                   (10795),  
   passenger-accident-fallen-on-board            (10796),  
   passenger-load                                (10797),  
   passenger-accident-other                      (10798),  
   passenger-sick-or-injured                     (10799),  
   right-of-way                                  (10800),  
   theft                                         (10801),  
   theft-of-service                              (10802),  
   waiting-to-get-relief-for-schedule-break      (10803),  
   waiting-to-get-relief-after-run-is-finished   (10804),  
   waiting-to-provide-relief                     (10805)
   } (0..65535)


TravelerGroupAffected ::= INTEGER  { 
   through-traffic                 (9473),  
   holiday-traffic                 (9474),  
   residents                       (9475),  
   visitors                        (9476),  
   long-distance-traffic           (9477),  
   local-traffic                   (9478),  
   regional-traffic                (9479),  
   arrivals                        (9480),  
   departures                      (9481),  
   airline-travelers               (9482),  
   commuter-airline-travelers      (9483),  
   domestic-airline-travelers      (9484),  
   international-airline-travelers (9485),  
   pedestrians                     (9486),  
   bicyclists                      (9487)   -- Hint: may be used as a traveler
                                            -- restriction, as in "bicycles prohibited on
                                            -- subways during rush hour" or "road closed
                                            -- to bicyclists"
   } (0..65535)


Units ::= INTEGER  { 
   -- Areas,  Distances  &  Speeds
   square-feet             (8705),  
   square-meters           (8706),  
   acres                   (8707),  
   hectares                (8708),  
   inches                  (8709),  
   feet                    (8710),  
   mile                    (8711),  -- Hint: used for offset as in "at mile 123"
                                    -- Alternative Rendering: milepost marker
   miles                   (8712),  -- Hint: Used for distance, as in "ending 5 miles"
   nautical-miles          (8713),  
   millimeters             (8714),  
   meters                  (8715),  
   kilometer               (8716),  -- Hint: used for offset as in "at kilometer 123"
   kilometers              (8717),  
   feet-per-second         (8718),  
   meters-per-second       (8719),  
   mPH                     (8720),  
   kPH                     (8721),  
   knots                   (8722),  
   elevation               (8766),  -- Typically followed by value and units
   -- Times,  Days  &  Dates
   aM                      (8723),  -- Both a time value and a radio band value. A
                                    -- number value may PRECEDE the unit value used in
                                    -- representing the frequency of a radio station
   pM                      (8724),  
   holiday                 (8726),  
   seconds                 (8727),  
   minutes                 (8728),  
   hours                   (8729),  
   days                    (8730),  -- Hint: useful for events occurring for at least 24
                                    -- hours
   weeks                   (8731),  
   months                  (8732),  
   other-times             (8767),  -- Typically used to represent a "default"
                                    -- allowed condition
   -- Days of the Week
   nSunday                 (8758),  
   nMonday                 (8759),  
   nTuesday                (8760),  
   nWednesday              (8761),  
   nThursday               (8762),  
   nFriday                 (8763),  
   nSaturday               (8764),  
   weekdays                (8765),  -- Alt text: Mon-Fri
   weekends                (8725),  -- In general date/time values can be better coded in
                                    -- other ways in most message sets
   -- Temps, Weights, Masses and Measurements
   degrees-Angle           (8733),  -- Used for latitude, longitude and bearing measured
                                    -- clockwise from North
   degrees-Celsius         (8734),  -- Alternate renderings possible
   degrees-Fahrenheit      (8735),  -- Alternate renderings possible
   grams                   (8736),  
   kilograms               (8737),  -- Also called a metric ton (1000kg or ~2204 lbs)
   ounces                  (8738),  
   pounds                  (8739),  
   tons                    (8740),  -- English Units (2000 lbs = 1 ton)
   fluid-ounces            (8741),  
   gallons                 (8742),  
   milliliters             (8743),  
   liters                  (8744),  
   kilograms-per-lane-mile (8745),  
   tons-per-lane-mile      (8746),  
   -- Misc.
   dollar                  (8747),  -- Alternative rendering: dollar symbol  Not to be
                                    -- used as the default value for this category
   percent                 (8748),  -- Alternative rendering: percent symbol
   grade                   (8757),  -- Typically preceded by a percent value entry
   time-delimiter          (8749),  -- Alternative rendering: "-"
   dollars                 (8750),  -- Alternative rendering can use local currency sign
   flight-number           (8751),  -- A number value may PRECEDE the unit value in use
   person-people           (8752),  
   response-plan           (8753),  -- A value may PRECEDE the unit value in use
                                    -- (involving a combination of numbers and/or
                                    -- letters)
   placard-type            (8754),  -- For hazmat class and division type designations, a
                                    -- value may PRECEDE the unit value in use
   placard-number          (8755),  -- For chemical designations, a value may PRECEDE the
                                    -- unit value in use
   fM                      (8756)   -- A number value may PRECEDE the unit value in use
                                    -- representing the frequency of a radio station
   } (0..65535)
   -- Used in conjunction with # values. In many ITS messages there are specific
   -- place holders (data elements) in the message set to send these values. This
   -- category shall not be used to circumvent message sets which support various units
   -- in this way


UnusualDriving ::= INTEGER  { 
   vehicle-traveling-wrong-way       (1793),  
   reckless-driver                   (1794),  -- Alternative Rendering: erratic driver
   prohibited-vehicle-on-roadway     (1795),  
   emergency-vehicles-on-roadway     (1796),  
   high-speed-emergency-vehicles     (1797),  
   high-speed-chase                  (1798),  
   -- Cancel Types
   dangerous-vehicle-warning-cleared (1918),  
   emergency-vehicle-warning-cleared (1919)
   } (0..65535)


ValidManeuvers ::= INTEGER  { 
   prohibit-None-Allowed-LU-LT-L45-S-R45-RT-RU (11264),  
   prohibit-RU-Allowed-LU-LT-L45-S-R45-RT      (11265),  -- All Maneuvers allowed
   prohibit-RT-Allowed-LU-LT-L45-S-R45-RU      (11266),  
   prohibit-RT-RU-Allowed-LU-LT-L45-S-R45      (11267),  
   prohibit-R45-Allowed-LU-LT-L45-S-RT-RU      (11268),  
   prohibit-R45-RU-Allowed-LU-LT-L45-S-RT      (11269),  
   prohibit-R45-RT-Allowed-LU-LT-L45-S-RU      (11270),  
   prohibit-R45-RT-RU-Allowed-LU-LT-L45-S      (11271),  -- Left or Straight Only
                                                         -- (R3-6), Right Turn prohibited
   prohibit-S-Allowed-LU-LT-L45-R45-RT-RU      (11272),  
   prohibit-S-RU-Allowed-LU-LT-L45-R45-RT      (11273),  
   prohibit-S-RT-Allowed-LU-LT-L45-R45-RU      (11274),  
   prohibit-S-RT-RU-Allowed-LU-LT-L45-R45      (11275),  
   prohibit-S-R45-Allowed-LU-LT-L45-RT-RU      (11276),  
   prohibit-S-R45-RU-Allowed-LU-LT-L45-RT      (11277),  
   prohibit-S-R45-RT-Allowed-LU-LT-L45-RU      (11278),  
   prohibit-S-R45-RT-RU-Allowed-LU-LT-L45      (11279),  
   prohibit-L45-Allowed-LU-LT-S-R45-RT-RU      (11280),  -- Left 45 deg turn
                                                         -- prohibited
   prohibit-L45-RU-Allowed-LU-LT-S-R45-RT      (11281),  
   prohibit-L45-RT-Allowed-LU-LT-S-R45-RU      (11282),  
   prohibit-L45-RT-RU-Allowed-LU-LT-S-R45      (11283),  
   prohibit-L45-R45-Allowed-LU-LT-S-RT-RU      (11284),  
   prohibit-L45-R45-RU-Allowed-LU-LT-S-RT      (11285),  
   prohibit-L45-R45-RT-Allowed-LU-LT-S-RU      (11286),  
   prohibit-L45-R45-RT-RU-Allowed-LU-LT-S      (11287),  
   prohibit-L45-S-Allowed-LU-LT-R45-RT-RU      (11288),  
   prohibit-L45-S-RU-Allowed-LU-LT-R45-RT      (11289),  
   prohibit-L45-S-RT-Allowed-LU-LT-R45-RU      (11290),  
   prohibit-L45-S-RT-RU-Allowed-LU-LT-R45      (11291),  
   prohibit-L45-S-R45-Allowed-LU-LT-RT-RU      (11292),  
   prohibit-L45-S-R45-RU-Allowed-LU-LT-RT      (11293),  
   prohibit-L45-S-R45-RT-Allowed-LU-LT-RU      (11294),  
   prohibit-L45-S-R45-RT-RU-Allowed-LU-LT      (11295),  -- Left U-Turn and Left
                                                         -- Turn Allowed
   prohibit-LT-Allowed-LU-L45-S-R45-RT-RU      (11296),  -- Left Turn Prohibited
                                                         -- (R3-2)
   prohibit-LT-RU-Allowed-LU-L45-S-R45-RT      (11297),  
   prohibit-LT-RT-Allowed-LU-L45-S-R45-RU      (11298),  -- Left and Right Turn
                                                         -- Prohibited  (R3-3), Straight
                                                         -- Only
   prohibit-LT-RT-RU-Allowed-LU-L45-S-R45      (11299),  
   prohibit-LT-R45-Allowed-LU-L45-S-RT-RU      (11300),  
   prohibit-LT-R45-RU-Allowed-LU-L45-S-RT      (11301),  
   prohibit-LT-R45-RT-Allowed-LU-L45-S-RU      (11302),  
   prohibit-LT-R45-RT-RU-Allowed-LU-L45-S      (11303),  
   prohibit-LT-S-Allowed-LU-L45-R45-RT-RU      (11304),  -- Straight Ahead
                                                         -- Prohibited
   prohibit-LT-S-RU-Allowed-LU-L45-R45-RT      (11305),  
   prohibit-LT-S-RT-Allowed-LU-L45-R45-RU      (11306),  
   prohibit-LT-S-RT-RU-Allowed-LU-L45-R45      (11307),  
   prohibit-LT-S-R45-Allowed-LU-L45-RT-RU      (11308),  
   prohibit-LT-S-R45-RU-Allowed-LU-L45-RT      (11309),  
   prohibit-LT-S-R45-RT-Allowed-LU-L45-RU      (11310),  
   prohibit-LT-S-R45-RT-RU-Allowed-LU-L45      (11311),  
   prohibit-LT-L45-Allowed-LU-S-R45-RT-RU      (11312),  
   prohibit-LT-L45-RU-Allowed-LU-S-R45-RT      (11313),  
   prohibit-LT-L45-RT-Allowed-LU-S-R45-RU      (11314),  
   prohibit-LT-L45-RT-RU-Allowed-LU-S-R45      (11315),  
   prohibit-LT-L45-R45-Allowed-LU-S-RT-RU      (11316),  
   prohibit-LT-L45-R45-RU-Allowed-LU-S-RT      (11317),  
   prohibit-LT-L45-R45-RT-Allowed-LU-S-RU      (11318),  
   prohibit-LT-L45-R45-RT-RU-Allowed-LU-S      (11319),  
   prohibit-LT-L45-S-Allowed-LU-R45-RT-RU      (11320),  
   prohibit-LT-L45-S-RU-Allowed-LU-R45-RT      (11321),  
   prohibit-LT-L45-S-RT-Allowed-LU-R45-RU      (11322),  
   prohibit-LT-L45-S-RT-RU-Allowed-LU-R45      (11323),  
   prohibit-LT-L45-S-R45-Allowed-LU-RT-RU      (11324),  
   prohibit-LT-L45-S-R45-RU-Allowed-LU-RT      (11325),  
   prohibit-LT-L45-S-R45-RT-Allowed-LU-RU      (11326),  
   prohibit-LT-L45-S-R45-RT-RU-Allowed-LU      (11327),  -- Left U-Turn Allowed
   prohibit-LU-Allowed-LT-L45-S-R45-RT-RU      (11328),  -- Left U-Turn Prohibited
                                                         -- (R3-4)
   prohibit-LU-RU-Allowed-LT-L45-S-R45-RT      (11329),  
   prohibit-LU-RT-Allowed-LT-L45-S-R45-RU      (11330),  
   prohibit-LU-RT-RU-Allowed-LT-L45-S-R45      (11331),  
   prohibit-LU-R45-Allowed-LT-L45-S-RT-RU      (11332),  
   prohibit-LU-R45-RU-Allowed-LT-L45-S-RT      (11333),  
   prohibit-LU-R45-RT-Allowed-LT-L45-S-RU      (11334),  
   prohibit-LU-R45-RT-RU-Allowed-LT-L45-S      (11335),  
   prohibit-LU-S-Allowed-LT-L45-R45-RT-RU      (11336),  
   prohibit-LU-S-RU-Allowed-LT-L45-R45-RT      (11337),  
   prohibit-LU-S-RT-Allowed-LT-L45-R45-RU      (11338),  
   prohibit-LU-S-RT-RU-Allowed-LT-L45-R45      (11339),  
   prohibit-LU-S-R45-Allowed-LT-L45-RT-RU      (11340),  
   prohibit-LU-S-R45-RU-Allowed-LT-L45-RT      (11341),  
   prohibit-LU-S-R45-RT-Allowed-LT-L45-RU      (11342),  
   prohibit-LU-S-R45-RT-RU-Allowed-LT-L45      (11343),  
   prohibit-LU-L45-Allowed-LT-S-R45-RT-RU      (11344),  
   prohibit-LU-L45-RU-Allowed-LT-S-R45-RT      (11345),  
   prohibit-LU-L45-RT-Allowed-LT-S-R45-RU      (11346),  
   prohibit-LU-L45-RT-RU-Allowed-LT-S-R45      (11347),  
   prohibit-LU-L45-R45-Allowed-LT-S-RT-RU      (11348),  
   prohibit-LU-L45-R45-RU-Allowed-LT-S-RT      (11349),  
   prohibit-LU-L45-R45-RT-Allowed-LT-S-RU      (11350),  
   prohibit-LU-L45-R45-RT-RU-Allowed-LT-S      (11351),  -- Left Turn and Straight
                                                         -- Ahead Only
   prohibit-LU-L45-S-Allowed-LT-R45-RT-RU      (11352),  
   prohibit-LU-L45-S-RU-Allowed-LT-R45-RT      (11353),  
   prohibit-LU-L45-S-RT-Allowed-LT-R45-RU      (11354),  
   prohibit-LU-L45-S-RT-RU-Allowed-LT-R45      (11355),  
   prohibit-LU-L45-S-R45-Allowed-LT-RT-RU      (11356),  
   prohibit-LU-L45-S-R45-RU-Allowed-LT-RT      (11357),  -- Left Turn and Right Turn
                                                         -- Only
   prohibit-LU-L45-S-R45-RT-Allowed-LT-RU      (11358),  
   prohibit-LU-L45-S-R45-RT-RU-Allowed-LT      (11359),  -- Left Turn Only  (R3-5)
   prohibit-LU-LT-Allowed-L45-S-R45-RT-RU      (11360),  -- Left U-Turn and Left
                                                         -- Turn Prohibited  (R3-18)
   prohibit-LU-LT-RU-Allowed-L45-S-R45-RT      (11361),  
   prohibit-LU-LT-RT-Allowed-L45-S-R45-RU      (11362),  
   prohibit-LU-LT-RT-RU-Allowed-L45-S-R45      (11363),  
   prohibit-LU-LT-R45-Allowed-L45-S-RT-RU      (11364),  
   prohibit-LU-LT-R45-RU-Allowed-L45-S-RT      (11365),  
   prohibit-LU-LT-R45-RT-Allowed-L45-S-RU      (11366),  
   prohibit-LU-LT-R45-RT-RU-Allowed-L45-S      (11367),  
   prohibit-LU-LT-S-Allowed-L45-R45-RT-RU      (11368),  
   prohibit-LU-LT-S-RU-Allowed-L45-R45-RT      (11369),  
   prohibit-LU-LT-S-RT-Allowed-L45-R45-RU      (11370),  
   prohibit-LU-LT-S-RT-RU-Allowed-L45-R45      (11371),  
   prohibit-LU-LT-S-R45-Allowed-L45-RT-RU      (11372),  
   prohibit-LU-LT-S-R45-RU-Allowed-L45-RT      (11373),  
   prohibit-LU-LT-S-R45-RT-Allowed-L45-RU      (11374),  
   prohibit-LU-LT-S-R45-RT-RU-Allowed-L45      (11375),  
   prohibit-LU-LT-L45-Allowed-S-R45-RT-RU      (11376),  -- Right Turn or Straight
                                                         -- Only  
   prohibit-LU-LT-L45-RU-Allowed-S-R45-RT      (11377),  
   prohibit-LU-LT-L45-RT-Allowed-S-R45-RU      (11378),  
   prohibit-LU-LT-L45-RT-RU-Allowed-S-R45      (11379),  
   prohibit-LU-LT-L45-R45-Allowed-S-RT-RU      (11380),  
   prohibit-LU-LT-L45-R45-RU-Allowed-S-RT      (11381),  
   prohibit-LU-LT-L45-R45-RT-Allowed-S-RU      (11382),  
   prohibit-LU-LT-L45-R45-RT-RU-Allowed-S      (11383),  -- Straight Ahead Only
                                                         -- (R3-5a)
   prohibit-LU-LT-L45-S-Allowed-R45-RT-RU      (11384),  
   prohibit-LU-LT-L45-S-RU-Allowed-R45-RT      (11385),  
   prohibit-LU-LT-L45-S-RT-Allowed-R45-RU      (11386),  
   prohibit-LU-LT-L45-S-RT-RU-Allowed-R45      (11387),  
   prohibit-LU-LT-L45-S-R45-Allowed-RT-RU      (11388),  
   prohibit-LU-LT-L45-S-R45-RU-Allowed-RT      (11389),  -- Right Turn Only 
   prohibit-LU-LT-L45-S-R45-RT-Allowed-RU      (11390),  
   prohibit-LU-LT-L45-S-R45-RT-RU-Allowed-None (11391)   -- All Maneuvers are
                                                         -- Prohibited
   } (0..65535)


VehicleGroupAffected ::= INTEGER  { 
   all-vehicles                               (9217),  
   bicycles                                   (9218),  
   motorcycles                                (9219),  -- to include mopeds as well
   cars                                       (9220),  -- (remapped from ERM value of
                                                       -- zero)
   light-vehicles                             (9221),  
   cars-and-light-vehicles                    (9222),  
   cars-with-trailers                         (9223),  
   cars-with-recreational-trailers            (9224),  
   vehicles-with-trailers                     (9225),  
   heavy-vehicles                             (9226),  
   trucks                                     (9227),  -- Use for RG-190
   buses                                      (9228),  
   articulated-buses                          (9229),  
   school-buses                               (9230),  
   vehicles-with-semi-trailers                (9231),  
   vehicles-with-double-trailers              (9232),  -- Alternative Rendering: western
                                                       -- doubles
   high-profile-vehicles                      (9233),  
   wide-vehicles                              (9234),  
   long-vehicles                              (9235),  
   hazardous-loads                            (9236),  
   exceptional-loads                          (9237),  
   abnormal-loads                             (9238),  
   convoys                                    (9239),  
   maintenance-vehicles                       (9240),  
   delivery-vehicles                          (9241),  
   vehicles-with-even-numbered-license-plates (9242),  
   vehicles-with-odd-numbered-license-plates  (9243),  
   vehicles-with-parking-permits              (9244),  
   vehicles-with-catalytic-converters         (9245),  
   vehicles-without-catalytic-converters      (9246),  
   gas-powered-vehicles                       (9247),  
   diesel-powered-vehicles                    (9248),  
   lPG-vehicles                               (9249),  
   military-convoys                           (9250),  
   military-vehicles                          (9251),  
   electric-powered-vehicles                  (9252),  
   hybrid-powered-vehicles                    (9253),  
   inherently-low-emission-vehicles            (9254),  
   commercial-vehicles                        (9255),  
   runaway-vehicles                           (9256),  
   vehicles-with-lugs                         (9257),  
   motor-driven-cycles                        (9258),  
   recreational-vehicles                      (9259),  -- Use for RVs
   non-motorized-vehicles                     (9260),  
   traffic                                    (9261)   -- Refers to all types of
                                                       -- motor traffic, all groups
   } (0..65535)
   -- Classification of vehicles and types of transport


VisibilityAndAirQuality ::= INTEGER  { 
   -- Visibility
   dense-fog                (5377),  -- This index is not to be used as a default value
                                     -- for this category
   fog                      (5378),  
   patchy-fog               (5379),  
   freezing-fog             (5380),  
   ice-fog                  (5405),  -- Different than freezing fog, ice fog occurs well
                                     -- below freezing temps and is quite common in the
                                     -- Fairbanks area.
   mist                     (5381),  
   haze                     (5382),  
   visibility-reduced       (5383),  
   visibility-blocked       (5404),  -- Used when signs, trees, etc., block the view
   white-out                (5384),  -- Alternative Rendering: Snow glare
   blowing-snow             (5385),  
   smoke-hazard             (5386),  
   spray-hazard             (5387),  
   low-sun-glare            (5388),  -- Do not use for snow glare
   snow-glare               (5389),  
   blowing-dust             (5390),  
   blowing-sand             (5391),  -- Hint: dune accumulations
   dust-storms              (5392),  
   sandstorms               (5393),  
   -- Air Quality
   air-quality-good         (5394),  
   air-quality-fair         (5395),  
   air-quality-poor         (5396),  
   air-quality-very-poor    (5397),  
   severe-exhaust-pollution (5398),  
   smog-alert               (5399),  
   pollen-count-high        (5400),  
   pollen-count-medium      (5401),  
   pollen-count-low         (5402),  
   swarms-of-insects        (5403),  
   -- Cancel Types
   fog-clearing             (5499),  
   visibility-improved      (5500),  
   fog-forecast-withdrawn   (5501),  
   pollution-alert-ended    (5502),  
   air-quality-improved     (5503)
   } (0..65535)


WarningAdvice ::= INTEGER  { 
   risk                                                 (6913),  -- Conditions are more
                                                                 -- likely than "normal"
   watch                                                (6914),  -- Conditions are
                                                                 -- favorable for an
                                                                 -- event to occur
   warning                                              (6915),  -- An event has occurred
                                                                 -- but is not (yet) near
   alert                                                (6916),  -- An event has occurred
                                                                 -- and it is near
   danger                                               (6917),  
   danger-of-explosion                                  (6918),  
   danger-of-fire                                       (6919),  
   extra-police-patrols-in-operation                    (6920),  
   look-out-for-vehicles-stopped-under-bridges          (6921),  
   increased-risk-of-accident                           (6922),  
   rescue-and-recovery-work-in-progress-at-sceneREMOVED (6923),  -- No long used, see
                                                                 -- item 2825
   police-at-scene                                      (6924),  
   emergency-vehicles-at-scene                          (6925),  
   traffic-being-directed-around-accident-area          (6926),  
   police-directing-traffic                             (6927),  
   rescue-workers-directing-traffic                     (6928),  
   repairs-in-progress                                  (6929),  
   pilot-car-in-operation                               (6930),  
   look-out-for-flagger                                 (6931),  -- Alternative
                                                                 -- Rendering: look out
                                                                 -- for flagman
   look-out-for-workers                                 (6952),  -- Alternative
                                                                 -- Rendering: workers
   police-checks-in-operation                           (6932),  -- Hint: all types of
                                                                 -- checks
   truck-check-point                                    (6937),  
   lockdown                                             (6935),  
   security-check-point                                 (6936),  
   single-occupancy-vehicle-check-point                 (6938),  
   mandatory-speed-limit-in-force                       (6933),  
   speed-limit-in-force-for-heavy-vehicles              (6934),  
   behind-you                                           (6950),  
   ride-with-traffic                                    (6953),  
   prepare-to-evacuate-area                             (6954),     
   avoid                                                (6955),  
   -- MUTCD Signs
   look                                                 (6939),  
   photo-enforced                                       (6940),  
   traffic-signs                                        (6951),  
   traffic-laws                                         (6941),  
   use-low-gear                                         (6942),  
   bridge-ices-before-road                              (6943),  
   speed-checked-by-radar                               (6944),  
   speed-checked-by-aircraft                            (6945),  
   fines                                                (6946),  
   fines-higher                                         (6947),  
   fines-doubled                                        (6948),  
   fines-tripled                                        (6949),  
   -- Cancel Types
   evacuation-canceled                                  (7033),  
   warning-canceled                                     (7034),  -- Canceling a warning
                                                                 -- may "revert" to a
                                                                 -- watch
   watch-canceled                                       (7035),  
   alert-canceled                                       (7036),  -- Canceling an alert
                                                                 -- may "revert" to a
                                                                 -- warning
   ended                                                (7037),  -- Hint: used for many
                                                                 -- sporting/special
                                                                 -- events
   cleared                                              (7038),  
   canceled                                             (7039)
   } (0..65535)


WeatherConditions ::= INTEGER  { 
   -- General Weather
   overcast                   (4609),  -- This index is not to be used as a default value
                                       -- for this category
   cloudy                     (4610),  
   mostly-cloudy              (4611),  
   partly-cloudy              (4612),  
   partly-sunny               (4613),  
   mostly-sunny               (4614),  
   sunny                      (4615),  
   fair-skies                 (4616),  
   clear-skies                (4617),  
   mostly-clear               (4618),  
   mostly-dry                 (4619),  
   dry                        (4620),  
   uV-index-very-high         (4621),  
   uV-index-high              (4622),  
   uV-index-moderate          (4623),  
   uV-index-low               (4624),  
   uV-index-very-low          (4625),  
   barometric-pressure        (4626),  -- Typically followed by a number and value
   ozone-alert                (4627),  
   -- Lighting Types
   lighting-unknown           (4628),  
   artificial-exterior-light  (4629),  
   artificial-interior-light  (4630),  
   darkness                   (4631),  -- Also used when not lighted
   dusk                       (4632),  
   dawn                       (4633),  
   moonlight                  (4634),  
   daylight                   (4635),  
   -- Cancel Types
   weather-forecast-withdrawn (4735)
   } (0..65535)


Winds ::= INTEGER  { 
   tornado                        (5121),  -- Note that this can be combined with "alert"
                                           -- "warning" etc. This index is not to be
                                           -- used as a default value for this category
   hurricane                      (5122),  
   hurricane-force-winds          (5123),  
   tropical-storm                 (5124),  
   gale-force-winds               (5125),  
   storm-force-winds              (5126),  
   strong-winds                   (5127),  
   moderate-winds                 (5128),  
   light-winds                    (5129),  
   calm                           (5130),  
   gusty-winds                    (5131),  
   crosswinds                     (5132),  
   windy                          (5133),  
   -- Cancel Types
   strong-winds-have-eased        (5246),  
   strong-wind-forecast-withdrawn (5247)
   } (0..65535)


WinterDrivingIndex ::= INTEGER  { 
   driving-conditions-good                (6401),  
   driving-conditions-fair                (6402),  
   difficult-driving-conditions           (6403),  
   very-difficult-driving-conditions      (6404),  
   hazardous-driving-conditions           (6405),  
   extremely-hazardous-driving-conditions (6406)
   } (0..65535)
   -- See also the restriction list for phrase items such as chains required


WinterDrivingRestrictions ::= INTEGER  { 
   winter-equipment-recommended       (6145),  
   winter-equipment-required          (6146),  
   snow-chains-recommended            (6147),  
   snow-chains-required               (6148),  
   snow-chains-prohibited             (6149),  
   studded-tires-prohibited           (6150),  
   snow-tires-recommended             (6151),  
   snow-tires-required                (6152),  
   four-wheel-drive-recommended       (6153),  
   four-wheel-drive-required          (6154),  
   snow-tires-or-chains-recommended   (6155),  
   snow-tires-or-chains-required      (6156),  
   -- Cancel Types
   winter-driving-requirements-lifted (6271)   -- In early editions this was incorrectly
                                               -- listed as code 6157
   } (0..65535)


ITISEventType ::= CHOICE  {
   trafficConditions                   TrafficConditions,
   accidentsAndIncidents               AccidentsAndIncidents,  
   closures                            Closures,   
   roadwork                            Roadwork,           
   obstruction                         Obstruction,     
   delayStatusCancellation             DelayStatusCancellation,  
   unusualDriving                      UnusualDriving,     
   mobileSituation                     MobileSituation, 
   deviceStatus                        DeviceStatus,    
   restrictionClass                    RestrictionClass,   
   incidentResponseStatus              IncidentResponseStatus,      
   disasters                           Disasters, 
   disturbances                        Disturbances, 
   sportingEvents                      SportingEvents,     
   specialEvents                       SpecialEvents,   
   parkingInformation                  ParkingInformation,
   systemInformation                   SystemInformation,     
   weatherConditions                   WeatherConditions,  
   precipitation                       Precipitation,      
   winds                               Winds,        
   visibilityAndAirQuality             VisibilityAndAirQuality,  
   temperature                         Temperature,     
   pavementConditions                  PavementConditions, 
   winterDrivingRestrictions           WinterDrivingRestrictions,   
   winterDrivingIndex                  WinterDrivingIndex, 
   suggestionAdvice                    SuggestionAdvice,   
   warningAdvice                       WarningAdvice,         
   adviceInstructionsRecommendations   AdviceInstructionsRecommendations, 
   adviceInstructionsMandatory         AdviceInstructionsMandatory,
   laneRoadway                         LaneRoadway,      
   alternateRoute                      AlternateRoute,   
   transitMode                         TransitMode,
   vehicleGroupAffected                VehicleGroupAffected,   
   travelerGroupAffected               TravelerGroupAffected,  
   responderGroupAffected              ResponderGroupAffected,
   incidentResponseEquipment           IncidentResponseEquipment,
   transitOperations                   TransitOperations,
   regulatorySigns                     RegulatoryAndWarningSigns
   }
   -- the set of  ITIS.ITISgroups
   -- a single code representing the top level grouping of ITIS sub-groups
   -- surrounded by the element tag of its sub group


ITIScodesAndText ::= SEQUENCE (SIZE(1..100)) OF SEQUENCE {
  item CHOICE    {
       itis ITIScodes,
       text ITIStext
       } -- # UNTAGGED
  }


END
